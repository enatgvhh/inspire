FME workspace xplan4.1Blob2inspire4.0Gml.fmw

Parameters:
- SourceDataset_POSTGIS = maske_xplan4.1-test   # Connection
- DestDataset_INSPIRE = D:\xplan2plu   # Destination Geography Markup Language (GML) File
- DestDataset_INSPIRE_5 = D:\xplan2inspire_4.1   # Destination Geography Markup Language (GML) File
- gml_id =   # MODE,WHERE GML Id

Readers:
- POSTGIS_1: POSTGIS from $(SourceDataset_POSTGIS)

Writers:
- INSPIRE_1: INSPIRE to $(DestDataset_INSPIRE)
- INSPIRE_2: INSPIRE to $(DestDataset_INSPIRE_5)

xplan41.gml_objects (reader POSTGIS_1)
    attributes: id serial,PrimaryKey, gml_id text,PrimaryKey, ft_type int2, binary_object bytea, plan_id text, plan_name text, internal_id text, rechtsstand text
    -> AttributeRemover_2
AttributeRemover_2
    REMOVE_ATTRS = id,plan_name,ft_type,plan_id,internal_id,rechtsstand
    -> X2I_BPPlan_extract [X2I_BPPlan_extract_Input]
X2I_BPPlan_extract
    BINARY_OBJECT = @Value(binary_object)
    GML_ID = @Value(gml_id)
    X2I_BPPlan_extract_Output -> FeatureMerger [REQUESTOR]
    X2I_BPPlan_extract_Output -> X2I_BPBereich_extract [X2I_BPBereich_extract_Input]
X2I_BPBereich_extract
    X2I_BPBereich_extract_Output -> FeatureMerger [SUPPLIER]
Note: Annahme: 1 BP_Plan = 1 BP_Bereich! (in HH OK)
FeatureMerger
    REJECT_NULL_MISSING_KEYS = No
    JOIN_KEYS = #@Value(gml_id) @Value(_result_gehoertZuPlan) STRING
    ATTR_CONFLICT_RES = Use Requestor
    MERGE_TYPE = Attributes Only
    IGNORE_NULLS = No
    PROCESS_DUPS = No
    SUPPLIERS_FIRST = No
    ATTR_ACCUM_MODE = Merge Supplier
    MERGED -> X2I_XPlanBaseClasses_filter [X2I_XPlanBaseClasses_filter_Input]
    MERGED -> AttributeRemover_3
AttributeRemover_3
    REMOVE_ATTRS = _result_versionBauGBDatum,_result_gehoertZuPlan,_result_versionBauNVODatum
    LIST_ATTRS = _results_list_planinhalt{} _results_list_externeReferenz{}
    -> FeatureMerger_2 [REQUESTOR]
X2I_XPlanBaseClasses_filter
    X2I_XPlanBaseClasses_filter_memberList_Output -> FeatureMerger_2 [SUPPLIER]
    X2I_XPlanBaseClasses_filter_restrictionList_Output -> FeatureMerger_3 [SUPPLIER]
    X2I_XPlanBaseClasses_filter_memberPassed_Output -> X2I_ZoningElement_extract [X2I_ZoningElement_extract_Input]
    X2I_XPlanBaseClasses_filter_restrictionPassed_Output -> X2I_SupplementaryRegulation_extract [X2I_SupplementaryRegulation_extract_Input]
CsmapReprojector
    RASTER_CELL_SIZE = Preserve Cells
    INTERPOLATION_TYPE_NAME = Nearest Neighbor
    DEST = EPSG:4258
    VERTICAL_HANDLING = Ignore heights and leave them unchanged
    REPROJECTED -> SpatialPlan (writer INSPIRE_2)
CsmapReprojector_2
    RASTER_CELL_SIZE = Preserve Cells
    INTERPOLATION_TYPE_NAME = Nearest Neighbor
    DEST = EPSG:4258
    VERTICAL_HANDLING = Ignore heights and leave them unchanged
    REPROJECTED -> ZoningElement (writer INSPIRE_2)
CsmapReprojector_3
    RASTER_CELL_SIZE = Preserve Cells
    INTERPOLATION_TYPE_NAME = Nearest Neighbor
    DEST = EPSG:4258
    VERTICAL_HANDLING = Ignore heights and leave them unchanged
    REPROJECTED -> SupplementaryRegulation (writer INSPIRE_2)

Bookmark: plu:SpatialPlan
FeatureMerger_2
    REJECT_NULL_MISSING_KEYS = No
    JOIN_KEYS = #@Value(gml_id_BP_Bereich) @Value(_result_gehoertZuBP_Bereich) AUTO
    ATTR_CONFLICT_RES = Use Requestor
    MERGE_TYPE = Attributes Only
    IGNORE_NULLS = No
    PROCESS_DUPS = No
    SUPPLIERS_FIRST = No
    ATTR_ACCUM_MODE = Merge Supplier
    MERGED -> FeatureMerger_3 [REQUESTOR]
    UNMERGED_REQUESTOR -> FeatureMerger_3 [REQUESTOR]
FeatureMerger_3
    REJECT_NULL_MISSING_KEYS = No
    JOIN_KEYS = #@Value(gml_id_BP_Bereich) @Value(_result_gehoertZuBP_Bereich) AUTO
    ATTR_CONFLICT_RES = Use Requestor
    MERGE_TYPE = Attributes Only
    IGNORE_NULLS = No
    PROCESS_DUPS = No
    SUPPLIERS_FIRST = No
    ATTR_ACCUM_MODE = Merge Supplier
    MERGED -> PythonCaller_createMemberAndRestrictionList
    UNMERGED_REQUESTOR -> PythonCaller_createMemberAndRestrictionList
PythonCaller_createMemberAndRestrictionList
    PYTHONSOURCE:
      import fme
      import fmeobjects

      def createMemberAndRestrictionList(feature):
          listMember = feature.getAttribute("_list_member{}.gml_id")
          listRestriction = feature.getAttribute("_list_restriction{}.gml_id")

          if listMember:
              for i in range(len(listMember)):
                  attrName = "member{" + str(i) + "}" + ".xlink_href"
                  feature.setAttribute(attrName,"#" + listMember[i])

          if listRestriction:
              for j in range(len(listRestriction)):
                  attrName = "restriction{" + str(j) + "}" + ".xlink_href"
                  feature.setAttribute(attrName,"#" + listRestriction[j])
    PYTHONSYMBOL = createMemberAndRestrictionList
    -> PythonCaller_createOfficialDocumentList
PythonCaller_createOfficialDocumentList
    PYTHONSOURCE:
      import fme
      import fmeobjects

      def createOfficialDocumentList(feature):
          listTexte = feature.getAttribute("_results_list_texte{}")
          listBegruendungsTexte = feature.getAttribute("_results_list_begruendungstexte{}")
          rasterBasis = feature.getAttribute("_result_rasterBasis")
          listDocuments = []

          if listTexte:
              for i in range(len(listTexte)):
                  listDocuments.append(listTexte[i])

          if listBegruendungsTexte:
              for j in range(len(listBegruendungsTexte)):
                  listDocuments.append(listBegruendungsTexte[j])

          if rasterBasis:
              listDocuments.append(rasterBasis)

          if len(listDocuments) > 0:
              for k in range(len(listDocuments)):
                  attrName = "officialDocument{" + str(k) + "}" + ".xlink_href"
                  feature.setAttribute(attrName,listDocuments[k])

          else:
              attrName1 = "officialDocument{0}.nilReason"
              attrName2 = "officialDocument{0}.xsi_nil"
              feature.setAttribute(attrName1,"other:unpopulated")
              feature.setAttribute(attrName2,"true")
    NEW_ATTRIBUTES = officialDocument{}.xlink_href
    PYTHONSYMBOL = createOfficialDocumentList
    -> X2I_spatialPlan_ordinanceList_create [X2I_spatialPlan_ordinanceList_create_Input]
X2I_spatialPlan_ordinanceList_create
    _RESULT_VERAENDERUNGSSPERREDATUM = @Value(_result_veraenderungssperreDatum)
    _RESULT_AUFSTELLUNGSBESCHLUSSDATUM = @Value(_result_aufstellungsbeschlussDatum)
    _RESULT_AENDERUNGENBISDATUM = @Value(_result_aenderungenBisDatum)
    _RESULT_RECHTSVERORDNUNGSDATUM = @Value(_result_rechtsverordnungsDatum)
    _RESULT_AUSFERTIGUNGSDATUM = @Value(_result_ausfertigungsDatum)
    _RESULT_TECHNHERSTELLDATUM = @Value(_result_technHerstellDatum)
    _RESULT_GENEHMIGUNGSDATUM = @Value(_result_genehmigungsDatum)
    _RESULT_SATZUNGSBESCHLUSSDATUM = @Value(_result_satzungsbeschlussDatum)
    X2I_spatialPlan_ordinanceList_create_Output -> AttributeValueMapper
    X2I_spatialPlan_ordinanceList_create_Output -> AttributeRemover_6
    X2I_spatialPlan_ordinanceList_create_Output -> AttributeRemover_4
Note: Annahme: planArt only 1! (in HH OK)
AttributeValueMapper
    SRC = _results_list_planArt{0}
    VAL_ATTR = _SpatialPlan.planTypeName
    LUT = 1000,6_Bebauungsplan,10000,6_3_EinfacherBPlan,10001,6_1_QualifizierterBPlan,3000,6_2_VorhabenbezogenerBPlan,4000,7_InnenbereichsSatzung,40000,7_1_KlarstellungsSatzung,40001,7_2_EntwicklungsSatzung,40002,7_3_ErgaenzungsSatzung,5000,8_AussenbereichsSatzung,7000,9_2_SonstigesPlanwerkStaedtebaurecht,9999,9_2_SonstigesPlanwerkStaedtebaurecht
    DIRECTION = Forward (Source To Destination)
    -> AttributeValueMapper_2
Note: Annahme: planArt only 1! (in HH OK)
AttributeValueMapper_2
    SRC = _results_list_planArt{0}
    VAL_ATTR = _SpatialPlan. levelOfSpatialPlan
    LUT = 1000,infraLocal,10000,infraLocal,10001,infraLocal,3000,infraLocal,4000,infraLocal,40000,infraLocal,40001,infraLocal,40002,infraLocal,5000,infraLocal,7000,infraLocal,9999,other
    DIRECTION = Forward (Source To Destination)
    -> AttributeValueMapper_3
AttributeValueMapper_3
    SRC = _result_rechtsstand
    VAL_ATTR = _SpatialPlan.processStepGeneral
    LUT = 1000,elaboration,2000,elaboration,2100,elaboration,2200,elaboration,2300,elaboration,2400,elaboration,3000,adoption,4000,legalForce,4500,obsolete,5000,obsolete
    DIRECTION = Forward (Source To Destination)
    -> PythonCaller_createOfficialDocumentSqlStatement
PythonCaller_createOfficialDocumentSqlStatement
    PYTHONSOURCE:
      import fme
      import fmeobjects

      def createOfficialDocumentSqlStatement(feature):
          listTexte = feature.getAttribute("_results_list_texte{}")
          listBegruendungsTexte = feature.getAttribute("_results_list_begruendungstexte{}")
          rasterBasis = feature.getAttribute("_result_rasterBasis")
          listDocuments = []

          sqlStrDocum = "SELECT gml_id, ft_type, binary_object FROM xplan41.gml_objects WHERE gml_id LIKE '"
          sqlStrOr = "' OR gml_id LIKE '"
          sqlStrEnd = "';"

          if listTexte:
              for i in range(len(listTexte)):
                  listDocuments.append(listTexte[i])

          if listBegruendungsTexte:
              for j in range(len(listBegruendungsTexte)):
                  listDocuments.append(listBegruendungsTexte[j])

          if rasterBasis:
              listDocuments.append(rasterBasis)

          if listDocuments:
              for k in range(len(listDocuments)):
                  if k == 0:
                      docRef = listDocuments[k].replace("#", "")
                      sqlStrDocum += docRef
                  else:
                      sqlStrDocum += sqlStrOr
                      docRef = listDocuments[k].replace("#", "")
                      sqlStrDocum += docRef

              sqlStrDocum += sqlStrEnd
              feature.setAttribute("sqlStrStatementOfficialDocument",sqlStrDocum)
    NEW_ATTRIBUTES = sqlStrStatementOfficialDocument
    PYTHONSYMBOL = createOfficialDocumentSqlStatement
    -> AttributeCreator
    -> Tester_20
Note: optionales Zielattribut für das optionale xplan-Attribute "hatGenerAttribut" wegelassen!
Note: optionales Ziel-Attribut für die xplan-Attribute "versionBauNVOText, versionBauGBText, / versionBauNVO, versionBauGB" wegelassen! Hieraus müsste je ein neues OfficialDocument / erzeugt werden!
AttributeCreator
    ATTR_TABLE:
      SET_TO gml_id = @Value(gml_id)
      SET_TO gml_identifier.codeSpace = http://inspire.ec.europa.eu/ids
      SET_TO gml_identifier = https://registry.gdi-de.org/id/de.hh/0a2b2809-dd93-45e6-bc0e-26093eb1122a/@Value(gml_id)
      SET_TO inspireId.Identifier.localId = @Value(gml_id)
      SET_TO inspireId.Identifier.namespace = https://registry.gdi-de.org/id/de.hh/0a2b2809-dd93-45e6-bc0e-26093eb1122a
      SET_TO beginLifespanVersion.nilReason = other:unpopulated
      SET_TO beginLifespanVersion.xsi_nil = true
      SET_TO endLifespanVersion.nilReason = other:unpopulated
      SET_TO endLifespanVersion.xsi_nil = true
      SET_TO officialTitle = @Value(_result_name)
      SET_TO levelOfSpatialPlan.xlink_href = http://inspire.ec.europa.eu/codelist/LevelOfSpatialPlanValue/@Value(_SpatialPlan. levelOfSpatialPlan)
      SET_TO alternativeTitle = FME_CONDITIONAL:DEFAULT_VALUE'_FME_NO_OP_'BOOL_OP;OR;COMPOSITE_TEST;<Unused>;TEST _result_nummer NOT_ATTRIBUTE_IS_MISSING _FME_BLANK_STRING_'@Value(_result_nummer)'FME_NUM_CONDITIONS2___
      SET_TO alternativeTitle.nilReason = FME_CONDITIONAL:DEFAULT_VALUE'_FME_NO_OP_'BOOL_OP;OR;COMPOSITE_TEST;<Unused>;TEST _result_nummer ATTRIBUTE_IS_MISSING _FME_BLANK_STRING_'other:unpopulated'FME_NUM_CONDITIONS2___
      SET_TO alternativeTitle.xsi_nil = FME_CONDITIONAL:DEFAULT_VALUE'_FME_NO_OP_'BOOL_OP;OR;COMPOSITE_TEST;<Unused>;TEST _result_nummer ATTRIBUTE_IS_MISSING _FME_BLANK_STRING_'true'FME_NUM_CONDITIONS2___
      SET_TO planTypeName.xlink_href = http://daten-hamburg.de/inspire/codelist/PlanTypeNameValue_Extension.xml#@Value(_SpatialPlan.planTypeName)
      SET_TO processStepGeneral.xlink_href = http://inspire.ec.europa.eu/codelist/ProcessStepGeneralValue/@Value(_SpatialPlan.processStepGeneral)
      SET_TO backgroundMap.nilReason = other:unpopulated
      SET_TO backgroundMap.xsi_nil = true
      SET_TO _ordinance{0}
      SET_TO _officialDocument{0}.xlink_href
      SET_TO _member{0}.xlink_href
      SET_TO _restriction{0}.xlink_href
      SET_TO validFrom = FME_CONDITIONAL:DEFAULT_VALUE'_FME_NO_OP_'BOOL_OP;OR;COMPOSITE_TEST;<Unused>;TEST _result_inkrafttretensDatum NOT_ATTRIBUTE_IS_MISSING _FME_BLANK_STRING_'@Value(_result_inkrafttretensDatum)'FME_NUM_CONDITIONS2___
      SET_TO _validFrom.nilReason = FME_CONDITIONAL:DEFAULT_VALUE'_FME_NO_OP_'BOOL_OP;OR;COMPOSITE_TEST;<Unused>;TEST _result_inkrafttretensDatum ATTRIBUTE_IS_MISSING _FME_BLANK_STRING_'other:unpopulated'FME_NUM_CONDITIONS2___
      SET_TO _validFrom.xsi_nil = FME_CONDITIONAL:DEFAULT_VALUE'_FME_NO_OP_'BOOL_OP;OR;COMPOSITE_TEST;<Unused>;TEST _result_inkrafttretensDatum ATTRIBUTE_IS_MISSING _FME_BLANK_STRING_'true'FME_NUM_CONDITIONS2___
      SET_TO validTo = FME_CONDITIONAL:DEFAULT_VALUE'_FME_NO_OP_'BOOL_OP;OR;COMPOSITE_TEST;<Unused>;TEST _result_untergangsDatum NOT_ATTRIBUTE_IS_MISSING _FME_BLANK_STRING_'@Value(_result_untergangsDatum)'FME_NUM_CONDITIONS2___
      SET_TO _validTo.nilReason = FME_CONDITIONAL:DEFAULT_VALUE'_FME_NO_OP_'BOOL_OP;OR;COMPOSITE_TEST;<Unused>;TEST _result_untergangsDatum ATTRIBUTE_IS_MISSING _FME_BLANK_STRING_'other:unpopulated'FME_NUM_CONDITIONS2___
      SET_TO _validTo.xsi_nil = FME_CONDITIONAL:DEFAULT_VALUE'_FME_NO_OP_'BOOL_OP;OR;COMPOSITE_TEST;<Unused>;TEST _result_untergangsDatum ATTRIBUTE_IS_MISSING _FME_BLANK_STRING_'true'FME_NUM_CONDITIONS2___
    -> AttributeRemover
AttributeRemover
    REMOVE_ATTRS = _result_genehmigungsDatum,_result_versionBauNVOText,_result_nummer,_result_ausfertigungsDatum,sqlStrStatementOfficialDocument,_result_versionBauGB,_result_name,_result_rechtsstand,gml_id_BP_Bereich,_result_aenderungenBisDatum,_result_veraenderungssperreDatum,_result_versionBauNVO,_result_untergangsDatum,_result_technHerstellDatum,_result_satzungsbeschlussDatum,_result_aufstellungsbeschlussDatum,_result_rasterBasis,_result_inkrafttretensDatum,_result_rechtsverordnungsDatum,_result_versionBauGBText
    LIST_ATTRS = _list_member{}.gml_id _list_restriction{}.gml_id _results_list_auslegungsEndDatum{} _results_list_auslegungsStartDatum{} _results_list_begruendungstexte{} _results_list_bereich{} _results_list_hatGenerAttribut{} _results_list_inhaltBPlan{} _results_list_planArt{} _results_list_texte{} _results_list_traegerbeteiligungsEndDatum{} _results_list_traegerbeteiligungsStartDatum{}
    -> GeometryReplacer_2

Bookmark: gml geometry
GeometryReplacer_2
    KIND_LONG = GML
    SOURCE = @Value(_result_raeumlicherGeltungsbereich)
    SRS_AXIS_ORDER_DISPLAY = Automatic
    REMOVE_ATTRIBUTE = Yes
    -> GeometryExtractor_3
GeometryExtractor_3
    OGCVERSION = 1.2
    KIND_LONG = OGC Well Known Binary
    REMOVE_GEOMETRY = Yes
    PREFER_POLYGON_OVER_SURFACE = Yes
    ATTR = _geometry_wkn
    -> GeometryReplacer_3
GeometryReplacer_3
    KIND_LONG = OGC Well Known Binary
    SOURCE = @Value(_geometry_wkn)
    ELLIPSOID_NAME = WGS84
    OUTPUT_POINT_DISPLAY = Point
    OGC_WKT_PRECISION_DISPLAY = 64-bit
    MSSQL_FORMAT_CHOICE = Geometry
    SRS_AXIS_ORDER_DISPLAY = Automatic
    REMOVE_ATTRIBUTE = Yes
    LETTERING = WGS84
    -> Orientor
Orientor
    KIND = RIGHT_HAND_RULE
    ORIENTED -> MultipleGeometryFilter
MultipleGeometryFilter
    CONTAINS -> GeometryPropertySetter_3
    NOT_CONTAINS -> GeometryPropertySetter_3
    INVALID -> Aggregator
Aggregator
    SEP = ,
    ORDERED = No
    GROUP_BY = gml_id
    AGGREGATE_TYPE = Homogeneous Collection (If Possible)
    MODE = Geometry - Assemble One Level
    ACCUM_ATTRS_NAME = Use Attributes From One Feature
    AGGREGATE -> GeometryPropertySetter_3
GeometryPropertySetter_3
    OVERWRITE_CHOICE = Yes
    SETTYPE_PARAM = Geometry Name
    GEOM_NAME_FIELD = extent
    SET -> CsmapReprojector
    SET -> SpatialPlan (writer INSPIRE_1) [off]

Bookmark: gml writer 4258
SpatialPlan (writer INSPIRE_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, inspireId.Identifier.localId xml_buffer, inspireId.Identifier.namespace xml_buffer, inspireId.Identifier.versionId xml_buffer, inspireId.Identifier.versionId.nilReason xml_buffer, inspireId.Identifier.versionId.xsi_nil xml_boolean, extent xml_geometry,
      beginLifespanVersion xml_datetime, beginLifespanVersion.nilReason xml_buffer, beginLifespanVersion.xsi_nil xml_boolean, officialTitle xml_buffer, levelOfSpatialPlan.owns xml_boolean, levelOfSpatialPlan.nilReason xml_buffer, levelOfSpatialPlan.gml_remoteSchema xml_buffer, levelOfSpatialPlan.xlink_href xml_buffer, levelOfSpatialPlan.xlink_title xml_buffer, endLifespanVersion xml_datetime, endLifespanVersion.nilReason xml_buffer, endLifespanVersion.xsi_nil xml_boolean, validFrom xml_date, validFrom.nilReason xml_buffer, validFrom.xsi_nil xml_boolean, validTo xml_date, validTo.nilReason xml_buffer, validTo.xsi_nil xml_boolean, alternativeTitle xml_buffer, alternativeTitle.nilReason xml_buffer, alternativeTitle.xsi_nil xml_boolean, planTypeName.owns xml_boolean, planTypeName.nilReason xml_buffer, planTypeName.gml_remoteSchema xml_buffer, planTypeName.xlink_href xml_buffer, planTypeName.xlink_title xml_buffer, processStepGeneral.owns xml_boolean, processStepGeneral.nilReason xml_buffer, processStepGeneral.gml_remoteSchema xml_buffer, processStepGeneral.xlink_href xml_buffer,
      processStepGeneral.xlink_title xml_buffer, processStepGeneral.xsi_nil xml_boolean, backgroundMap.nilReason xml_buffer, backgroundMap.xsi_nil xml_boolean, backgroundMap.BackgroundMapValue.backgroundMapDate xml_datetime, backgroundMap.BackgroundMapValue.backgroundMapReference xml_buffer, backgroundMap.BackgroundMapValue.backgroudMapURI xml_buffer, backgroundMap.BackgroundMapValue.backgroudMapURI.nilReason xml_buffer, backgroundMap.BackgroundMapValue.backgroudMapURI.xsi_nil xml_boolean, ordinance{}.nilReason xml_buffer, ordinance{}.xsi_nil xml_boolean, ordinance{}.OrdinanceValue.ordinanceDate xml_datetime, ordinance{}.OrdinanceValue.ordinanceReference xml_buffer, officialDocument{}.owns xml_boolean, officialDocument{}.nilReason xml_buffer, officialDocument{}.gml_remoteSchema xml_buffer, officialDocument{}.xlink_href xml_buffer, officialDocument{}.xlink_title xml_buffer, officialDocument{}.xsi_nil xml_boolean, member{}.owns xml_boolean, member{}.nilReason xml_buffer, member{}.gml_remoteSchema xml_buffer, member{}.xlink_href xml_buffer, member{}.xlink_title xml_buffer, restriction{}.owns xml_boolean, restriction{}.nilReason xml_buffer, restriction{}.gml_remoteSchema xml_buffer, restriction{}.xlink_href xml_buffer, restriction{}.xlink_title xml_buffer
ZoningElement (writer INSPIRE_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, inspireId.Identifier.localId xml_buffer, inspireId.Identifier.namespace xml_buffer, inspireId.Identifier.versionId xml_buffer, inspireId.Identifier.versionId.nilReason xml_buffer, inspireId.Identifier.versionId.xsi_nil xml_boolean, geometry xml_geometry,
      validFrom xml_date, validFrom.nilReason xml_buffer, validFrom.xsi_nil xml_boolean, validTo xml_date, validTo.nilReason xml_buffer, validTo.xsi_nil xml_boolean, hilucsLandUse{}.owns xml_boolean, hilucsLandUse{}.nilReason xml_buffer, hilucsLandUse{}.gml_remoteSchema xml_buffer, hilucsLandUse{}.xlink_href xml_buffer, hilucsLandUse{}.xlink_title xml_buffer, beginLifespanVersion xml_datetime, beginLifespanVersion.nilReason xml_buffer, beginLifespanVersion.xsi_nil xml_boolean, hilucsPresence.nilReason xml_buffer, hilucsPresence.xsi_nil xml_boolean, hilucsPresence.HILUCSPresence.orderedList{}.owns xml_boolean, hilucsPresence.HILUCSPresence.orderedList{}.nilReason xml_buffer, hilucsPresence.HILUCSPresence.orderedList{}.gml_remoteSchema xml_buffer, hilucsPresence.HILUCSPresence.orderedList{}.xlink_href xml_buffer, hilucsPresence.HILUCSPresence.orderedList{}.xlink_title xml_buffer, hilucsPresence.HILUCSPresence.percentageList{}.HILUCSPercentage.hilucsValue.owns xml_boolean, hilucsPresence.HILUCSPresence.percentageList{}.HILUCSPercentage.hilucsValue.nilReason xml_buffer, hilucsPresence.HILUCSPresence.percentageList{}.HILUCSPercentage.hilucsValue.gml_remoteSchema xml_buffer, hilucsPresence.HILUCSPresence.percentageList{}.HILUCSPercentage.hilucsValue.xlink_href xml_buffer, hilucsPresence.HILUCSPresence.percentageList{}.HILUCSPercentage.hilucsValue.xlink_title xml_buffer, hilucsPresence.HILUCSPresence.percentageList{}.HILUCSPercentage.percentage xml_int64, specificLandUse{}.owns xml_boolean, specificLandUse{}.nilReason xml_buffer, specificLandUse{}.gml_remoteSchema xml_buffer,
      specificLandUse{}.xlink_href xml_buffer, specificLandUse{}.xlink_title xml_buffer, specificLandUse{}.xsi_nil xml_boolean, specificPresence.nilReason xml_buffer, specificPresence.xsi_nil xml_boolean, specificPresence.SpecificPresence.orderedList{}.owns xml_boolean, specificPresence.SpecificPresence.orderedList{}.nilReason xml_buffer, specificPresence.SpecificPresence.orderedList{}.gml_remoteSchema xml_buffer, specificPresence.SpecificPresence.orderedList{}.xlink_href xml_buffer, specificPresence.SpecificPresence.orderedList{}.xlink_title xml_buffer, specificPresence.SpecificPresence.percentageList{}.SpecificPercentage.specificValue.owns xml_boolean, specificPresence.SpecificPresence.percentageList{}.SpecificPercentage.specificValue.nilReason xml_buffer, specificPresence.SpecificPresence.percentageList{}.SpecificPercentage.specificValue.gml_remoteSchema xml_buffer, specificPresence.SpecificPresence.percentageList{}.SpecificPercentage.specificValue.xlink_href xml_buffer, specificPresence.SpecificPresence.percentageList{}.SpecificPercentage.specificValue.xlink_title xml_buffer, specificPresence.SpecificPresence.percentageList{}.SpecificPercentage.percentage xml_int64, regulationNature.owns xml_boolean, regulationNature.nilReason xml_buffer, regulationNature.gml_remoteSchema xml_buffer, regulationNature.xlink_href xml_buffer, regulationNature.xlink_title xml_buffer, endLifespanVersion xml_datetime, endLifespanVersion.nilReason xml_buffer, endLifespanVersion.xsi_nil xml_boolean, processStepGeneral.owns xml_boolean, processStepGeneral.nilReason xml_buffer, processStepGeneral.gml_remoteSchema xml_buffer, processStepGeneral.xlink_href xml_buffer, processStepGeneral.xlink_title xml_buffer, processStepGeneral.xsi_nil xml_boolean,
      backgroundMap.nilReason xml_buffer, backgroundMap.xsi_nil xml_boolean, backgroundMap.BackgroundMapValue.backgroundMapDate xml_datetime, backgroundMap.BackgroundMapValue.backgroundMapReference xml_buffer, backgroundMap.BackgroundMapValue.backgroudMapURI xml_buffer, backgroundMap.BackgroundMapValue.backgroudMapURI.nilReason xml_buffer, backgroundMap.BackgroundMapValue.backgroudMapURI.xsi_nil xml_boolean, dimensioningIndication{}.nilReason xml_buffer, dimensioningIndication{}.xsi_nil xml_boolean, dimensioningIndication{}.DimensioningIndicationMeasureValue.indicationReference xml_buffer, dimensioningIndication{}.DimensioningIndicationMeasureValue.value xml_real64, dimensioningIndication{}.DimensioningIndicationMeasureValue.value.uom xml_buffer, dimensioningIndication{}.DimensioningIndicationRealValue.indicationReference xml_buffer, dimensioningIndication{}.DimensioningIndicationRealValue.value xml_real64, dimensioningIndication{}.DimensioningIndicationIntegerValue.indicationReference xml_buffer, dimensioningIndication{}.DimensioningIndicationIntegerValue.value xml_int64, dimensioningIndication{}.DimensioningIndicationCharacterValue.indicationReference xml_buffer, dimensioningIndication{}.DimensioningIndicationCharacterValue.value xml_buffer, dimensioningIndication{}.DimensioningIndicationValue.indicationReference xml_buffer, officialDocument{}.owns xml_boolean, officialDocument{}.nilReason xml_buffer, officialDocument{}.gml_remoteSchema xml_buffer, officialDocument{}.xlink_href xml_buffer, officialDocument{}.xlink_title xml_buffer, officialDocument{}.xsi_nil xml_boolean, plan.owns xml_boolean, plan.nilReason xml_buffer, plan.gml_remoteSchema xml_buffer, plan.xlink_href xml_buffer, plan.xlink_title xml_buffer
OfficialDocumentation (writer INSPIRE_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, inspireId.Identifier.localId xml_buffer, inspireId.Identifier.namespace xml_buffer, inspireId.Identifier.versionId xml_buffer, inspireId.Identifier.versionId.nilReason xml_buffer, inspireId.Identifier.versionId.xsi_nil xml_boolean, legislationCitation.nilReason xml_buffer,
      legislationCitation.gml_remoteSchema xml_buffer, legislationCitation.xlink_href xml_buffer, legislationCitation.xlink_title xml_buffer, legislationCitation.owns xml_boolean, legislationCitation.xsi_nil xml_boolean, legislationCitation.LegislationCitation.gml_id xml_buffer, legislationCitation.LegislationCitation.gml_metaDataProperty{}.about xml_buffer, legislationCitation.LegislationCitation.gml_metaDataProperty{}.nilReason xml_buffer, legislationCitation.LegislationCitation.gml_metaDataProperty{}.gml_remoteSchema xml_buffer, legislationCitation.LegislationCitation.gml_metaDataProperty{}.xlink_href xml_buffer, legislationCitation.LegislationCitation.gml_metaDataProperty{}.xlink_title xml_buffer, legislationCitation.LegislationCitation.gml_metaDataProperty{}.gml_GenericMetaData xml_xml, legislationCitation.LegislationCitation.gml_metaDataProperty{}.gml_GenericMetaData.gml_id xml_buffer, legislationCitation.LegislationCitation.gml_description xml_buffer, legislationCitation.LegislationCitation.gml_description.nilReason xml_buffer, legislationCitation.LegislationCitation.gml_description.gml_remoteSchema xml_buffer, legislationCitation.LegislationCitation.gml_description.xlink_href xml_buffer, legislationCitation.LegislationCitation.gml_description.xlink_title xml_buffer, legislationCitation.LegislationCitation.gml_descriptionReference.owns xml_boolean, legislationCitation.LegislationCitation.gml_descriptionReference.nilReason xml_buffer, legislationCitation.LegislationCitation.gml_descriptionReference.gml_remoteSchema xml_buffer, legislationCitation.LegislationCitation.gml_descriptionReference.xlink_href xml_buffer, legislationCitation.LegislationCitation.gml_descriptionReference.xlink_title xml_buffer, legislationCitation.LegislationCitation.gml_identifier xml_buffer, legislationCitation.LegislationCitation.gml_identifier.codeSpace xml_buffer, legislationCitation.LegislationCitation.gml_name{} xml_buffer, legislationCitation.LegislationCitation.gml_name{}.codeSpace xml_buffer, legislationCitation.LegislationCitation.name xml_buffer, legislationCitation.LegislationCitation.shortName xml_buffer, legislationCitation.LegislationCitation.shortName.nilReason xml_buffer,
      legislationCitation.LegislationCitation.shortName.xsi_nil xml_boolean, legislationCitation.LegislationCitation.date.nilReason xml_buffer, legislationCitation.LegislationCitation.date.owns xml_boolean, legislationCitation.LegislationCitation.date.xsi_nil xml_boolean, legislationCitation.LegislationCitation.date.CI_Date.id xml_buffer, legislationCitation.LegislationCitation.date.CI_Date.uuid xml_buffer, legislationCitation.LegislationCitation.date.CI_Date.date.gco_nilReason xml_buffer, legislationCitation.LegislationCitation.date.CI_Date.date.Date xml_buffer, legislationCitation.LegislationCitation.date.CI_Date.date.Date.xsi_nil xml_boolean, legislationCitation.LegislationCitation.date.CI_Date.date.DateTime xml_datetime, legislationCitation.LegislationCitation.date.CI_Date.dateType.nilReason xml_buffer, legislationCitation.LegislationCitation.date.CI_Date.dateType.CI_DateTypeCode xml_buffer, legislationCitation.LegislationCitation.date.CI_Date.dateType.CI_DateTypeCode.codeList xml_buffer, legislationCitation.LegislationCitation.date.CI_Date.dateType.CI_DateTypeCode.codeListValue xml_buffer, legislationCitation.LegislationCitation.date.CI_Date.dateType.CI_DateTypeCode.codeSpace xml_buffer, legislationCitation.LegislationCitation.link{} xml_buffer, legislationCitation.LegislationCitation.link{}.nilReason xml_buffer, legislationCitation.LegislationCitation.link{}.xsi_nil xml_boolean, legislationCitation.LegislationCitation.specificReference{} xml_buffer, legislationCitation.LegislationCitation.specificReference{}.nilReason xml_buffer, legislationCitation.LegislationCitation.specificReference{}.xsi_nil xml_boolean, legislationCitation.LegislationCitation.identificationNumber xml_buffer, legislationCitation.LegislationCitation.officialDocumentNumber xml_buffer, legislationCitation.LegislationCitation.dateEnteredIntoForce xml_buffer, legislationCitation.LegislationCitation.dateEnteredIntoForce.frame xml_buffer, legislationCitation.LegislationCitation.dateEnteredIntoForce.calendarEraName xml_buffer, legislationCitation.LegislationCitation.dateEnteredIntoForce.indeterminatePosition xml_char(7), legislationCitation.LegislationCitation.dateRepealed xml_buffer, legislationCitation.LegislationCitation.dateRepealed.frame xml_buffer, legislationCitation.LegislationCitation.dateRepealed.calendarEraName xml_buffer,
      legislationCitation.LegislationCitation.dateRepealed.indeterminatePosition xml_char(7), legislationCitation.LegislationCitation.level.owns xml_boolean, legislationCitation.LegislationCitation.level.nilReason xml_buffer, legislationCitation.LegislationCitation.level.gml_remoteSchema xml_buffer, legislationCitation.LegislationCitation.level.xlink_href xml_buffer, legislationCitation.LegislationCitation.level.xlink_title xml_buffer, legislationCitation.LegislationCitation.journalCitation.OfficialJournalInformation.officialJournalIdentification xml_buffer, legislationCitation.LegislationCitation.journalCitation.OfficialJournalInformation.ISSN xml_buffer, legislationCitation.LegislationCitation.journalCitation.OfficialJournalInformation.ISBN xml_buffer, legislationCitation.LegislationCitation.journalCitation.OfficialJournalInformation.linkToJournal xml_buffer, regulationText xml_buffer, regulationText.nilReason xml_buffer, regulationText.xsi_nil xml_boolean, planDocument.nilReason xml_buffer, planDocument.gml_remoteSchema xml_buffer, planDocument.xlink_href xml_buffer, planDocument.xlink_title xml_buffer, planDocument.owns xml_boolean, planDocument.xsi_nil xml_boolean, planDocument.LegislationCitation.gml_id xml_buffer, planDocument.LegislationCitation.gml_metaDataProperty{}.about xml_buffer, planDocument.LegislationCitation.gml_metaDataProperty{}.nilReason xml_buffer, planDocument.LegislationCitation.gml_metaDataProperty{}.gml_remoteSchema xml_buffer, planDocument.LegislationCitation.gml_metaDataProperty{}.xlink_href xml_buffer, planDocument.LegislationCitation.gml_metaDataProperty{}.xlink_title xml_buffer, planDocument.LegislationCitation.gml_metaDataProperty{}.gml_GenericMetaData xml_xml, planDocument.LegislationCitation.gml_metaDataProperty{}.gml_GenericMetaData.gml_id xml_buffer, planDocument.LegislationCitation.gml_description xml_buffer, planDocument.LegislationCitation.gml_description.nilReason xml_buffer, planDocument.LegislationCitation.gml_description.gml_remoteSchema xml_buffer,
      planDocument.LegislationCitation.gml_description.xlink_href xml_buffer, planDocument.LegislationCitation.gml_description.xlink_title xml_buffer, planDocument.LegislationCitation.gml_descriptionReference.owns xml_boolean, planDocument.LegislationCitation.gml_descriptionReference.nilReason xml_buffer, planDocument.LegislationCitation.gml_descriptionReference.gml_remoteSchema xml_buffer, planDocument.LegislationCitation.gml_descriptionReference.xlink_href xml_buffer, planDocument.LegislationCitation.gml_descriptionReference.xlink_title xml_buffer, planDocument.LegislationCitation.gml_identifier xml_buffer, planDocument.LegislationCitation.gml_identifier.codeSpace xml_buffer, planDocument.LegislationCitation.gml_name{} xml_buffer, planDocument.LegislationCitation.gml_name{}.codeSpace xml_buffer, planDocument.LegislationCitation.name xml_buffer, planDocument.LegislationCitation.shortName xml_buffer, planDocument.LegislationCitation.shortName.nilReason xml_buffer, planDocument.LegislationCitation.shortName.xsi_nil xml_boolean, planDocument.LegislationCitation.date.nilReason xml_buffer, planDocument.LegislationCitation.date.owns xml_boolean, planDocument.LegislationCitation.date.xsi_nil xml_boolean, planDocument.LegislationCitation.date.CI_Date.id xml_buffer, planDocument.LegislationCitation.date.CI_Date.uuid xml_buffer, planDocument.LegislationCitation.date.CI_Date.date.gco_nilReason xml_buffer, planDocument.LegislationCitation.date.CI_Date.date.Date xml_buffer, planDocument.LegislationCitation.date.CI_Date.date.Date.xsi_nil xml_boolean, planDocument.LegislationCitation.date.CI_Date.date.DateTime xml_datetime, planDocument.LegislationCitation.date.CI_Date.dateType.nilReason xml_buffer, planDocument.LegislationCitation.date.CI_Date.dateType.CI_DateTypeCode xml_buffer, planDocument.LegislationCitation.date.CI_Date.dateType.CI_DateTypeCode.codeList xml_buffer, planDocument.LegislationCitation.date.CI_Date.dateType.CI_DateTypeCode.codeListValue xml_buffer, planDocument.LegislationCitation.date.CI_Date.dateType.CI_DateTypeCode.codeSpace xml_buffer, planDocument.LegislationCitation.link{} xml_buffer,
      planDocument.LegislationCitation.link{}.nilReason xml_buffer, planDocument.LegislationCitation.link{}.xsi_nil xml_boolean, planDocument.LegislationCitation.specificReference{} xml_buffer, planDocument.LegislationCitation.specificReference{}.nilReason xml_buffer, planDocument.LegislationCitation.specificReference{}.xsi_nil xml_boolean, planDocument.LegislationCitation.identificationNumber xml_buffer, planDocument.LegislationCitation.officialDocumentNumber xml_buffer, planDocument.LegislationCitation.dateEnteredIntoForce xml_buffer, planDocument.LegislationCitation.dateEnteredIntoForce.frame xml_buffer, planDocument.LegislationCitation.dateEnteredIntoForce.calendarEraName xml_buffer, planDocument.LegislationCitation.dateEnteredIntoForce.indeterminatePosition xml_char(7), planDocument.LegislationCitation.dateRepealed xml_buffer, planDocument.LegislationCitation.dateRepealed.frame xml_buffer, planDocument.LegislationCitation.dateRepealed.calendarEraName xml_buffer, planDocument.LegislationCitation.dateRepealed.indeterminatePosition xml_char(7), planDocument.LegislationCitation.level.owns xml_boolean, planDocument.LegislationCitation.level.nilReason xml_buffer, planDocument.LegislationCitation.level.gml_remoteSchema xml_buffer, planDocument.LegislationCitation.level.xlink_href xml_buffer, planDocument.LegislationCitation.level.xlink_title xml_buffer, planDocument.LegislationCitation.journalCitation.OfficialJournalInformation.officialJournalIdentification xml_buffer, planDocument.LegislationCitation.journalCitation.OfficialJournalInformation.ISSN xml_buffer, planDocument.LegislationCitation.journalCitation.OfficialJournalInformation.ISBN xml_buffer, planDocument.LegislationCitation.journalCitation.OfficialJournalInformation.linkToJournal xml_buffer, planDocument.DocumentCitation.gml_id xml_buffer, planDocument.DocumentCitation.gml_metaDataProperty{}.about xml_buffer, planDocument.DocumentCitation.gml_metaDataProperty{}.nilReason xml_buffer, planDocument.DocumentCitation.gml_metaDataProperty{}.gml_remoteSchema xml_buffer, planDocument.DocumentCitation.gml_metaDataProperty{}.xlink_href xml_buffer, planDocument.DocumentCitation.gml_metaDataProperty{}.xlink_title xml_buffer,
      planDocument.DocumentCitation.gml_metaDataProperty{}.gml_GenericMetaData xml_xml, planDocument.DocumentCitation.gml_metaDataProperty{}.gml_GenericMetaData.gml_id xml_buffer, planDocument.DocumentCitation.gml_description xml_buffer, planDocument.DocumentCitation.gml_description.nilReason xml_buffer, planDocument.DocumentCitation.gml_description.gml_remoteSchema xml_buffer, planDocument.DocumentCitation.gml_description.xlink_href xml_buffer, planDocument.DocumentCitation.gml_description.xlink_title xml_buffer, planDocument.DocumentCitation.gml_descriptionReference.owns xml_boolean, planDocument.DocumentCitation.gml_descriptionReference.nilReason xml_buffer, planDocument.DocumentCitation.gml_descriptionReference.gml_remoteSchema xml_buffer, planDocument.DocumentCitation.gml_descriptionReference.xlink_href xml_buffer, planDocument.DocumentCitation.gml_descriptionReference.xlink_title xml_buffer, planDocument.DocumentCitation.gml_identifier xml_buffer, planDocument.DocumentCitation.gml_identifier.codeSpace xml_buffer, planDocument.DocumentCitation.gml_name{} xml_buffer, planDocument.DocumentCitation.gml_name{}.codeSpace xml_buffer, planDocument.DocumentCitation.name xml_buffer, planDocument.DocumentCitation.shortName xml_buffer, planDocument.DocumentCitation.shortName.nilReason xml_buffer, planDocument.DocumentCitation.shortName.xsi_nil xml_boolean, planDocument.DocumentCitation.date.nilReason xml_buffer, planDocument.DocumentCitation.date.owns xml_boolean, planDocument.DocumentCitation.date.xsi_nil xml_boolean, planDocument.DocumentCitation.date.CI_Date.id xml_buffer, planDocument.DocumentCitation.date.CI_Date.uuid xml_buffer, planDocument.DocumentCitation.date.CI_Date.date.gco_nilReason xml_buffer, planDocument.DocumentCitation.date.CI_Date.date.Date xml_buffer, planDocument.DocumentCitation.date.CI_Date.date.Date.xsi_nil xml_boolean, planDocument.DocumentCitation.date.CI_Date.date.DateTime xml_datetime, planDocument.DocumentCitation.date.CI_Date.dateType.nilReason xml_buffer,
      planDocument.DocumentCitation.date.CI_Date.dateType.CI_DateTypeCode xml_buffer, planDocument.DocumentCitation.date.CI_Date.dateType.CI_DateTypeCode.codeList xml_buffer, planDocument.DocumentCitation.date.CI_Date.dateType.CI_DateTypeCode.codeListValue xml_buffer, planDocument.DocumentCitation.date.CI_Date.dateType.CI_DateTypeCode.codeSpace xml_buffer, planDocument.DocumentCitation.link{} xml_buffer, planDocument.DocumentCitation.link{}.nilReason xml_buffer, planDocument.DocumentCitation.link{}.xsi_nil xml_boolean, planDocument.DocumentCitation.specificReference{} xml_buffer, planDocument.DocumentCitation.specificReference{}.nilReason xml_buffer, planDocument.DocumentCitation.specificReference{}.xsi_nil xml_boolean
SupplementaryRegulation (writer INSPIRE_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, validFrom xml_date, validFrom.nilReason xml_buffer, validFrom.xsi_nil xml_boolean, validTo xml_date, validTo.nilReason xml_buffer, validTo.xsi_nil xml_boolean,
      specificSupplementaryRegulation{}.owns xml_boolean, specificSupplementaryRegulation{}.nilReason xml_buffer, specificSupplementaryRegulation{}.gml_remoteSchema xml_buffer, specificSupplementaryRegulation{}.xlink_href xml_buffer, specificSupplementaryRegulation{}.xlink_title xml_buffer, specificSupplementaryRegulation{}.xsi_nil xml_boolean, processStepGeneral.owns xml_boolean, processStepGeneral.nilReason xml_buffer, processStepGeneral.gml_remoteSchema xml_buffer, processStepGeneral.xlink_href xml_buffer, processStepGeneral.xlink_title xml_buffer, processStepGeneral.xsi_nil xml_boolean, backgroundMap.nilReason xml_buffer, backgroundMap.xsi_nil xml_boolean, backgroundMap.BackgroundMapValue.backgroundMapDate xml_datetime, backgroundMap.BackgroundMapValue.backgroundMapReference xml_buffer, backgroundMap.BackgroundMapValue.backgroudMapURI xml_buffer, backgroundMap.BackgroundMapValue.backgroudMapURI.nilReason xml_buffer, backgroundMap.BackgroundMapValue.backgroudMapURI.xsi_nil xml_boolean, beginLifespanVersion xml_datetime, beginLifespanVersion.nilReason xml_buffer, beginLifespanVersion.xsi_nil xml_boolean, dimensioningIndication{}.nilReason xml_buffer, dimensioningIndication{}.xsi_nil xml_boolean, dimensioningIndication{}.DimensioningIndicationMeasureValue.indicationReference xml_buffer, dimensioningIndication{}.DimensioningIndicationMeasureValue.value xml_real64, dimensioningIndication{}.DimensioningIndicationMeasureValue.value.uom xml_buffer, dimensioningIndication{}.DimensioningIndicationRealValue.indicationReference xml_buffer, dimensioningIndication{}.DimensioningIndicationRealValue.value xml_real64, dimensioningIndication{}.DimensioningIndicationIntegerValue.indicationReference xml_buffer,
      dimensioningIndication{}.DimensioningIndicationIntegerValue.value xml_int64, dimensioningIndication{}.DimensioningIndicationCharacterValue.indicationReference xml_buffer, dimensioningIndication{}.DimensioningIndicationCharacterValue.value xml_buffer, dimensioningIndication{}.DimensioningIndicationValue.indicationReference xml_buffer, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, geometry xml_geometry, inheritedFromOtherPlans xml_boolean, inheritedFromOtherPlans.nilReason xml_buffer, inheritedFromOtherPlans.xsi_nil xml_boolean, specificRegulationNature xml_buffer, specificRegulationNature.nilReason xml_buffer, specificRegulationNature.xsi_nil xml_boolean, name{} xml_buffer, name{}.nilReason xml_buffer, name{}.xsi_nil xml_boolean, regulationNature.owns xml_boolean, regulationNature.nilReason xml_buffer, regulationNature.gml_remoteSchema xml_buffer, regulationNature.xlink_href xml_buffer, regulationNature.xlink_title xml_buffer, supplementaryRegulation{}.owns xml_boolean, supplementaryRegulation{}.nilReason xml_buffer, supplementaryRegulation{}.gml_remoteSchema xml_buffer,
      supplementaryRegulation{}.xlink_href xml_buffer, supplementaryRegulation{}.xlink_title xml_buffer, officialDocument{}.owns xml_boolean, officialDocument{}.nilReason xml_buffer, officialDocument{}.gml_remoteSchema xml_buffer, officialDocument{}.xlink_href xml_buffer, officialDocument{}.xlink_title xml_buffer, officialDocument{}.xsi_nil xml_boolean, plan.owns xml_boolean, plan.nilReason xml_buffer, plan.gml_remoteSchema xml_buffer, plan.xlink_href xml_buffer, plan.xlink_title xml_buffer

Bookmark: gml writer 25832
SpatialPlan (writer INSPIRE_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, inspireId.Identifier.localId xml_buffer, inspireId.Identifier.namespace xml_buffer, inspireId.Identifier.versionId xml_buffer, inspireId.Identifier.versionId.nilReason xml_buffer, inspireId.Identifier.versionId.xsi_nil xml_boolean, extent xml_geometry,
      beginLifespanVersion xml_datetime, beginLifespanVersion.nilReason xml_buffer, beginLifespanVersion.xsi_nil xml_boolean, officialTitle xml_buffer, levelOfSpatialPlan.owns xml_boolean, levelOfSpatialPlan.nilReason xml_buffer, levelOfSpatialPlan.gml_remoteSchema xml_buffer, levelOfSpatialPlan.xlink_href xml_buffer, levelOfSpatialPlan.xlink_title xml_buffer, endLifespanVersion xml_datetime, endLifespanVersion.nilReason xml_buffer, endLifespanVersion.xsi_nil xml_boolean, validFrom xml_date, validFrom.nilReason xml_buffer, validFrom.xsi_nil xml_boolean, validTo xml_date, validTo.nilReason xml_buffer, validTo.xsi_nil xml_boolean, alternativeTitle xml_buffer, alternativeTitle.nilReason xml_buffer, alternativeTitle.xsi_nil xml_boolean, planTypeName.owns xml_boolean, planTypeName.nilReason xml_buffer, planTypeName.gml_remoteSchema xml_buffer, planTypeName.xlink_href xml_buffer, planTypeName.xlink_title xml_buffer, processStepGeneral.owns xml_boolean, processStepGeneral.nilReason xml_buffer, processStepGeneral.gml_remoteSchema xml_buffer, processStepGeneral.xlink_href xml_buffer,
      processStepGeneral.xlink_title xml_buffer, processStepGeneral.xsi_nil xml_boolean, backgroundMap.nilReason xml_buffer, backgroundMap.xsi_nil xml_boolean, backgroundMap.BackgroundMapValue.backgroundMapDate xml_datetime, backgroundMap.BackgroundMapValue.backgroundMapReference xml_buffer, backgroundMap.BackgroundMapValue.backgroudMapURI xml_buffer, backgroundMap.BackgroundMapValue.backgroudMapURI.nilReason xml_buffer, backgroundMap.BackgroundMapValue.backgroudMapURI.xsi_nil xml_boolean, ordinance{}.nilReason xml_buffer, ordinance{}.xsi_nil xml_boolean, ordinance{}.OrdinanceValue.ordinanceDate xml_datetime, ordinance{}.OrdinanceValue.ordinanceReference xml_buffer, officialDocument{}.owns xml_boolean, officialDocument{}.nilReason xml_buffer, officialDocument{}.gml_remoteSchema xml_buffer, officialDocument{}.xlink_href xml_buffer, officialDocument{}.xlink_title xml_buffer, officialDocument{}.xsi_nil xml_boolean, member{}.owns xml_boolean, member{}.nilReason xml_buffer, member{}.gml_remoteSchema xml_buffer, member{}.xlink_href xml_buffer, member{}.xlink_title xml_buffer, restriction{}.owns xml_boolean, restriction{}.nilReason xml_buffer, restriction{}.gml_remoteSchema xml_buffer, restriction{}.xlink_href xml_buffer, restriction{}.xlink_title xml_buffer
ZoningElement (writer INSPIRE_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, inspireId.Identifier.localId xml_buffer, inspireId.Identifier.namespace xml_buffer, inspireId.Identifier.versionId xml_buffer, inspireId.Identifier.versionId.nilReason xml_buffer, inspireId.Identifier.versionId.xsi_nil xml_boolean, geometry xml_geometry,
      validFrom xml_date, validFrom.nilReason xml_buffer, validFrom.xsi_nil xml_boolean, validTo xml_date, validTo.nilReason xml_buffer, validTo.xsi_nil xml_boolean, hilucsLandUse{}.owns xml_boolean, hilucsLandUse{}.nilReason xml_buffer, hilucsLandUse{}.gml_remoteSchema xml_buffer, hilucsLandUse{}.xlink_href xml_buffer, hilucsLandUse{}.xlink_title xml_buffer, beginLifespanVersion xml_datetime, beginLifespanVersion.nilReason xml_buffer, beginLifespanVersion.xsi_nil xml_boolean, hilucsPresence.nilReason xml_buffer, hilucsPresence.xsi_nil xml_boolean, hilucsPresence.HILUCSPresence.orderedList{}.owns xml_boolean, hilucsPresence.HILUCSPresence.orderedList{}.nilReason xml_buffer, hilucsPresence.HILUCSPresence.orderedList{}.gml_remoteSchema xml_buffer, hilucsPresence.HILUCSPresence.orderedList{}.xlink_href xml_buffer, hilucsPresence.HILUCSPresence.orderedList{}.xlink_title xml_buffer, hilucsPresence.HILUCSPresence.percentageList{}.HILUCSPercentage.hilucsValue.owns xml_boolean, hilucsPresence.HILUCSPresence.percentageList{}.HILUCSPercentage.hilucsValue.nilReason xml_buffer, hilucsPresence.HILUCSPresence.percentageList{}.HILUCSPercentage.hilucsValue.gml_remoteSchema xml_buffer, hilucsPresence.HILUCSPresence.percentageList{}.HILUCSPercentage.hilucsValue.xlink_href xml_buffer, hilucsPresence.HILUCSPresence.percentageList{}.HILUCSPercentage.hilucsValue.xlink_title xml_buffer, hilucsPresence.HILUCSPresence.percentageList{}.HILUCSPercentage.percentage xml_int64, specificLandUse{}.owns xml_boolean, specificLandUse{}.nilReason xml_buffer, specificLandUse{}.gml_remoteSchema xml_buffer,
      specificLandUse{}.xlink_href xml_buffer, specificLandUse{}.xlink_title xml_buffer, specificLandUse{}.xsi_nil xml_boolean, specificPresence.nilReason xml_buffer, specificPresence.xsi_nil xml_boolean, specificPresence.SpecificPresence.orderedList{}.owns xml_boolean, specificPresence.SpecificPresence.orderedList{}.nilReason xml_buffer, specificPresence.SpecificPresence.orderedList{}.gml_remoteSchema xml_buffer, specificPresence.SpecificPresence.orderedList{}.xlink_href xml_buffer, specificPresence.SpecificPresence.orderedList{}.xlink_title xml_buffer, specificPresence.SpecificPresence.percentageList{}.SpecificPercentage.specificValue.owns xml_boolean, specificPresence.SpecificPresence.percentageList{}.SpecificPercentage.specificValue.nilReason xml_buffer, specificPresence.SpecificPresence.percentageList{}.SpecificPercentage.specificValue.gml_remoteSchema xml_buffer, specificPresence.SpecificPresence.percentageList{}.SpecificPercentage.specificValue.xlink_href xml_buffer, specificPresence.SpecificPresence.percentageList{}.SpecificPercentage.specificValue.xlink_title xml_buffer, specificPresence.SpecificPresence.percentageList{}.SpecificPercentage.percentage xml_int64, regulationNature.owns xml_boolean, regulationNature.nilReason xml_buffer, regulationNature.gml_remoteSchema xml_buffer, regulationNature.xlink_href xml_buffer, regulationNature.xlink_title xml_buffer, endLifespanVersion xml_datetime, endLifespanVersion.nilReason xml_buffer, endLifespanVersion.xsi_nil xml_boolean, processStepGeneral.owns xml_boolean, processStepGeneral.nilReason xml_buffer, processStepGeneral.gml_remoteSchema xml_buffer, processStepGeneral.xlink_href xml_buffer, processStepGeneral.xlink_title xml_buffer, processStepGeneral.xsi_nil xml_boolean,
      backgroundMap.nilReason xml_buffer, backgroundMap.xsi_nil xml_boolean, backgroundMap.BackgroundMapValue.backgroundMapDate xml_datetime, backgroundMap.BackgroundMapValue.backgroundMapReference xml_buffer, backgroundMap.BackgroundMapValue.backgroudMapURI xml_buffer, backgroundMap.BackgroundMapValue.backgroudMapURI.nilReason xml_buffer, backgroundMap.BackgroundMapValue.backgroudMapURI.xsi_nil xml_boolean, dimensioningIndication{}.nilReason xml_buffer, dimensioningIndication{}.xsi_nil xml_boolean, dimensioningIndication{}.DimensioningIndicationMeasureValue.indicationReference xml_buffer, dimensioningIndication{}.DimensioningIndicationMeasureValue.value xml_real64, dimensioningIndication{}.DimensioningIndicationMeasureValue.value.uom xml_buffer, dimensioningIndication{}.DimensioningIndicationRealValue.indicationReference xml_buffer, dimensioningIndication{}.DimensioningIndicationRealValue.value xml_real64, dimensioningIndication{}.DimensioningIndicationIntegerValue.indicationReference xml_buffer, dimensioningIndication{}.DimensioningIndicationIntegerValue.value xml_int64, dimensioningIndication{}.DimensioningIndicationCharacterValue.indicationReference xml_buffer, dimensioningIndication{}.DimensioningIndicationCharacterValue.value xml_buffer, dimensioningIndication{}.DimensioningIndicationValue.indicationReference xml_buffer, officialDocument{}.owns xml_boolean, officialDocument{}.nilReason xml_buffer, officialDocument{}.gml_remoteSchema xml_buffer, officialDocument{}.xlink_href xml_buffer, officialDocument{}.xlink_title xml_buffer, officialDocument{}.xsi_nil xml_boolean, plan.owns xml_boolean, plan.nilReason xml_buffer, plan.gml_remoteSchema xml_buffer, plan.xlink_href xml_buffer, plan.xlink_title xml_buffer
OfficialDocumentation (writer INSPIRE_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, inspireId.Identifier.localId xml_buffer, inspireId.Identifier.namespace xml_buffer, inspireId.Identifier.versionId xml_buffer, inspireId.Identifier.versionId.nilReason xml_buffer, inspireId.Identifier.versionId.xsi_nil xml_boolean, legislationCitation.nilReason xml_buffer,
      legislationCitation.gml_remoteSchema xml_buffer, legislationCitation.xlink_href xml_buffer, legislationCitation.xlink_title xml_buffer, legislationCitation.owns xml_boolean, legislationCitation.xsi_nil xml_boolean, legislationCitation.LegislationCitation.gml_id xml_buffer, legislationCitation.LegislationCitation.gml_metaDataProperty{}.about xml_buffer, legislationCitation.LegislationCitation.gml_metaDataProperty{}.nilReason xml_buffer, legislationCitation.LegislationCitation.gml_metaDataProperty{}.gml_remoteSchema xml_buffer, legislationCitation.LegislationCitation.gml_metaDataProperty{}.xlink_href xml_buffer, legislationCitation.LegislationCitation.gml_metaDataProperty{}.xlink_title xml_buffer, legislationCitation.LegislationCitation.gml_metaDataProperty{}.gml_GenericMetaData xml_xml, legislationCitation.LegislationCitation.gml_metaDataProperty{}.gml_GenericMetaData.gml_id xml_buffer, legislationCitation.LegislationCitation.gml_description xml_buffer, legislationCitation.LegislationCitation.gml_description.nilReason xml_buffer, legislationCitation.LegislationCitation.gml_description.gml_remoteSchema xml_buffer, legislationCitation.LegislationCitation.gml_description.xlink_href xml_buffer, legislationCitation.LegislationCitation.gml_description.xlink_title xml_buffer, legislationCitation.LegislationCitation.gml_descriptionReference.owns xml_boolean, legislationCitation.LegislationCitation.gml_descriptionReference.nilReason xml_buffer, legislationCitation.LegislationCitation.gml_descriptionReference.gml_remoteSchema xml_buffer, legislationCitation.LegislationCitation.gml_descriptionReference.xlink_href xml_buffer, legislationCitation.LegislationCitation.gml_descriptionReference.xlink_title xml_buffer, legislationCitation.LegislationCitation.gml_identifier xml_buffer, legislationCitation.LegislationCitation.gml_identifier.codeSpace xml_buffer, legislationCitation.LegislationCitation.gml_name{} xml_buffer, legislationCitation.LegislationCitation.gml_name{}.codeSpace xml_buffer, legislationCitation.LegislationCitation.name xml_buffer, legislationCitation.LegislationCitation.shortName xml_buffer, legislationCitation.LegislationCitation.shortName.nilReason xml_buffer,
      legislationCitation.LegislationCitation.shortName.xsi_nil xml_boolean, legislationCitation.LegislationCitation.date.nilReason xml_buffer, legislationCitation.LegislationCitation.date.owns xml_boolean, legislationCitation.LegislationCitation.date.xsi_nil xml_boolean, legislationCitation.LegislationCitation.date.CI_Date.id xml_buffer, legislationCitation.LegislationCitation.date.CI_Date.uuid xml_buffer, legislationCitation.LegislationCitation.date.CI_Date.date.gco_nilReason xml_buffer, legislationCitation.LegislationCitation.date.CI_Date.date.Date xml_buffer, legislationCitation.LegislationCitation.date.CI_Date.date.Date.xsi_nil xml_boolean, legislationCitation.LegislationCitation.date.CI_Date.date.DateTime xml_datetime, legislationCitation.LegislationCitation.date.CI_Date.dateType.nilReason xml_buffer, legislationCitation.LegislationCitation.date.CI_Date.dateType.CI_DateTypeCode xml_buffer, legislationCitation.LegislationCitation.date.CI_Date.dateType.CI_DateTypeCode.codeList xml_buffer, legislationCitation.LegislationCitation.date.CI_Date.dateType.CI_DateTypeCode.codeListValue xml_buffer, legislationCitation.LegislationCitation.date.CI_Date.dateType.CI_DateTypeCode.codeSpace xml_buffer, legislationCitation.LegislationCitation.link{} xml_buffer, legislationCitation.LegislationCitation.link{}.nilReason xml_buffer, legislationCitation.LegislationCitation.link{}.xsi_nil xml_boolean, legislationCitation.LegislationCitation.specificReference{} xml_buffer, legislationCitation.LegislationCitation.specificReference{}.nilReason xml_buffer, legislationCitation.LegislationCitation.specificReference{}.xsi_nil xml_boolean, legislationCitation.LegislationCitation.identificationNumber xml_buffer, legislationCitation.LegislationCitation.officialDocumentNumber xml_buffer, legislationCitation.LegislationCitation.dateEnteredIntoForce xml_buffer, legislationCitation.LegislationCitation.dateEnteredIntoForce.frame xml_buffer, legislationCitation.LegislationCitation.dateEnteredIntoForce.calendarEraName xml_buffer, legislationCitation.LegislationCitation.dateEnteredIntoForce.indeterminatePosition xml_char(7), legislationCitation.LegislationCitation.dateRepealed xml_buffer, legislationCitation.LegislationCitation.dateRepealed.frame xml_buffer, legislationCitation.LegislationCitation.dateRepealed.calendarEraName xml_buffer,
      legislationCitation.LegislationCitation.dateRepealed.indeterminatePosition xml_char(7), legislationCitation.LegislationCitation.level.owns xml_boolean, legislationCitation.LegislationCitation.level.nilReason xml_buffer, legislationCitation.LegislationCitation.level.gml_remoteSchema xml_buffer, legislationCitation.LegislationCitation.level.xlink_href xml_buffer, legislationCitation.LegislationCitation.level.xlink_title xml_buffer, legislationCitation.LegislationCitation.journalCitation.OfficialJournalInformation.officialJournalIdentification xml_buffer, legislationCitation.LegislationCitation.journalCitation.OfficialJournalInformation.ISSN xml_buffer, legislationCitation.LegislationCitation.journalCitation.OfficialJournalInformation.ISBN xml_buffer, legislationCitation.LegislationCitation.journalCitation.OfficialJournalInformation.linkToJournal xml_buffer, regulationText xml_buffer, regulationText.nilReason xml_buffer, regulationText.xsi_nil xml_boolean, planDocument.nilReason xml_buffer, planDocument.gml_remoteSchema xml_buffer, planDocument.xlink_href xml_buffer, planDocument.xlink_title xml_buffer, planDocument.owns xml_boolean, planDocument.xsi_nil xml_boolean, planDocument.LegislationCitation.gml_id xml_buffer, planDocument.LegislationCitation.gml_metaDataProperty{}.about xml_buffer, planDocument.LegislationCitation.gml_metaDataProperty{}.nilReason xml_buffer, planDocument.LegislationCitation.gml_metaDataProperty{}.gml_remoteSchema xml_buffer, planDocument.LegislationCitation.gml_metaDataProperty{}.xlink_href xml_buffer, planDocument.LegislationCitation.gml_metaDataProperty{}.xlink_title xml_buffer, planDocument.LegislationCitation.gml_metaDataProperty{}.gml_GenericMetaData xml_xml, planDocument.LegislationCitation.gml_metaDataProperty{}.gml_GenericMetaData.gml_id xml_buffer, planDocument.LegislationCitation.gml_description xml_buffer, planDocument.LegislationCitation.gml_description.nilReason xml_buffer, planDocument.LegislationCitation.gml_description.gml_remoteSchema xml_buffer,
      planDocument.LegislationCitation.gml_description.xlink_href xml_buffer, planDocument.LegislationCitation.gml_description.xlink_title xml_buffer, planDocument.LegislationCitation.gml_descriptionReference.owns xml_boolean, planDocument.LegislationCitation.gml_descriptionReference.nilReason xml_buffer, planDocument.LegislationCitation.gml_descriptionReference.gml_remoteSchema xml_buffer, planDocument.LegislationCitation.gml_descriptionReference.xlink_href xml_buffer, planDocument.LegislationCitation.gml_descriptionReference.xlink_title xml_buffer, planDocument.LegislationCitation.gml_identifier xml_buffer, planDocument.LegislationCitation.gml_identifier.codeSpace xml_buffer, planDocument.LegislationCitation.gml_name{} xml_buffer, planDocument.LegislationCitation.gml_name{}.codeSpace xml_buffer, planDocument.LegislationCitation.name xml_buffer, planDocument.LegislationCitation.shortName xml_buffer, planDocument.LegislationCitation.shortName.nilReason xml_buffer, planDocument.LegislationCitation.shortName.xsi_nil xml_boolean, planDocument.LegislationCitation.date.nilReason xml_buffer, planDocument.LegislationCitation.date.owns xml_boolean, planDocument.LegislationCitation.date.xsi_nil xml_boolean, planDocument.LegislationCitation.date.CI_Date.id xml_buffer, planDocument.LegislationCitation.date.CI_Date.uuid xml_buffer, planDocument.LegislationCitation.date.CI_Date.date.gco_nilReason xml_buffer, planDocument.LegislationCitation.date.CI_Date.date.Date xml_buffer, planDocument.LegislationCitation.date.CI_Date.date.Date.xsi_nil xml_boolean, planDocument.LegislationCitation.date.CI_Date.date.DateTime xml_datetime, planDocument.LegislationCitation.date.CI_Date.dateType.nilReason xml_buffer, planDocument.LegislationCitation.date.CI_Date.dateType.CI_DateTypeCode xml_buffer, planDocument.LegislationCitation.date.CI_Date.dateType.CI_DateTypeCode.codeList xml_buffer, planDocument.LegislationCitation.date.CI_Date.dateType.CI_DateTypeCode.codeListValue xml_buffer, planDocument.LegislationCitation.date.CI_Date.dateType.CI_DateTypeCode.codeSpace xml_buffer, planDocument.LegislationCitation.link{} xml_buffer,
      planDocument.LegislationCitation.link{}.nilReason xml_buffer, planDocument.LegislationCitation.link{}.xsi_nil xml_boolean, planDocument.LegislationCitation.specificReference{} xml_buffer, planDocument.LegislationCitation.specificReference{}.nilReason xml_buffer, planDocument.LegislationCitation.specificReference{}.xsi_nil xml_boolean, planDocument.LegislationCitation.identificationNumber xml_buffer, planDocument.LegislationCitation.officialDocumentNumber xml_buffer, planDocument.LegislationCitation.dateEnteredIntoForce xml_buffer, planDocument.LegislationCitation.dateEnteredIntoForce.frame xml_buffer, planDocument.LegislationCitation.dateEnteredIntoForce.calendarEraName xml_buffer, planDocument.LegislationCitation.dateEnteredIntoForce.indeterminatePosition xml_char(7), planDocument.LegislationCitation.dateRepealed xml_buffer, planDocument.LegislationCitation.dateRepealed.frame xml_buffer, planDocument.LegislationCitation.dateRepealed.calendarEraName xml_buffer, planDocument.LegislationCitation.dateRepealed.indeterminatePosition xml_char(7), planDocument.LegislationCitation.level.owns xml_boolean, planDocument.LegislationCitation.level.nilReason xml_buffer, planDocument.LegislationCitation.level.gml_remoteSchema xml_buffer, planDocument.LegislationCitation.level.xlink_href xml_buffer, planDocument.LegislationCitation.level.xlink_title xml_buffer, planDocument.LegislationCitation.journalCitation.OfficialJournalInformation.officialJournalIdentification xml_buffer, planDocument.LegislationCitation.journalCitation.OfficialJournalInformation.ISSN xml_buffer, planDocument.LegislationCitation.journalCitation.OfficialJournalInformation.ISBN xml_buffer, planDocument.LegislationCitation.journalCitation.OfficialJournalInformation.linkToJournal xml_buffer, planDocument.DocumentCitation.gml_id xml_buffer, planDocument.DocumentCitation.gml_metaDataProperty{}.about xml_buffer, planDocument.DocumentCitation.gml_metaDataProperty{}.nilReason xml_buffer, planDocument.DocumentCitation.gml_metaDataProperty{}.gml_remoteSchema xml_buffer, planDocument.DocumentCitation.gml_metaDataProperty{}.xlink_href xml_buffer, planDocument.DocumentCitation.gml_metaDataProperty{}.xlink_title xml_buffer,
      planDocument.DocumentCitation.gml_metaDataProperty{}.gml_GenericMetaData xml_xml, planDocument.DocumentCitation.gml_metaDataProperty{}.gml_GenericMetaData.gml_id xml_buffer, planDocument.DocumentCitation.gml_description xml_buffer, planDocument.DocumentCitation.gml_description.nilReason xml_buffer, planDocument.DocumentCitation.gml_description.gml_remoteSchema xml_buffer, planDocument.DocumentCitation.gml_description.xlink_href xml_buffer, planDocument.DocumentCitation.gml_description.xlink_title xml_buffer, planDocument.DocumentCitation.gml_descriptionReference.owns xml_boolean, planDocument.DocumentCitation.gml_descriptionReference.nilReason xml_buffer, planDocument.DocumentCitation.gml_descriptionReference.gml_remoteSchema xml_buffer, planDocument.DocumentCitation.gml_descriptionReference.xlink_href xml_buffer, planDocument.DocumentCitation.gml_descriptionReference.xlink_title xml_buffer, planDocument.DocumentCitation.gml_identifier xml_buffer, planDocument.DocumentCitation.gml_identifier.codeSpace xml_buffer, planDocument.DocumentCitation.gml_name{} xml_buffer, planDocument.DocumentCitation.gml_name{}.codeSpace xml_buffer, planDocument.DocumentCitation.name xml_buffer, planDocument.DocumentCitation.shortName xml_buffer, planDocument.DocumentCitation.shortName.nilReason xml_buffer, planDocument.DocumentCitation.shortName.xsi_nil xml_boolean, planDocument.DocumentCitation.date.nilReason xml_buffer, planDocument.DocumentCitation.date.owns xml_boolean, planDocument.DocumentCitation.date.xsi_nil xml_boolean, planDocument.DocumentCitation.date.CI_Date.id xml_buffer, planDocument.DocumentCitation.date.CI_Date.uuid xml_buffer, planDocument.DocumentCitation.date.CI_Date.date.gco_nilReason xml_buffer, planDocument.DocumentCitation.date.CI_Date.date.Date xml_buffer, planDocument.DocumentCitation.date.CI_Date.date.Date.xsi_nil xml_boolean, planDocument.DocumentCitation.date.CI_Date.date.DateTime xml_datetime, planDocument.DocumentCitation.date.CI_Date.dateType.nilReason xml_buffer,
      planDocument.DocumentCitation.date.CI_Date.dateType.CI_DateTypeCode xml_buffer, planDocument.DocumentCitation.date.CI_Date.dateType.CI_DateTypeCode.codeList xml_buffer, planDocument.DocumentCitation.date.CI_Date.dateType.CI_DateTypeCode.codeListValue xml_buffer, planDocument.DocumentCitation.date.CI_Date.dateType.CI_DateTypeCode.codeSpace xml_buffer, planDocument.DocumentCitation.link{} xml_buffer, planDocument.DocumentCitation.link{}.nilReason xml_buffer, planDocument.DocumentCitation.link{}.xsi_nil xml_boolean, planDocument.DocumentCitation.specificReference{} xml_buffer, planDocument.DocumentCitation.specificReference{}.nilReason xml_buffer, planDocument.DocumentCitation.specificReference{}.xsi_nil xml_boolean
SupplementaryRegulation (writer INSPIRE_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, validFrom xml_date, validFrom.nilReason xml_buffer, validFrom.xsi_nil xml_boolean, validTo xml_date, validTo.nilReason xml_buffer, validTo.xsi_nil xml_boolean,
      specificSupplementaryRegulation{}.owns xml_boolean, specificSupplementaryRegulation{}.nilReason xml_buffer, specificSupplementaryRegulation{}.gml_remoteSchema xml_buffer, specificSupplementaryRegulation{}.xlink_href xml_buffer, specificSupplementaryRegulation{}.xlink_title xml_buffer, specificSupplementaryRegulation{}.xsi_nil xml_boolean, processStepGeneral.owns xml_boolean, processStepGeneral.nilReason xml_buffer, processStepGeneral.gml_remoteSchema xml_buffer, processStepGeneral.xlink_href xml_buffer, processStepGeneral.xlink_title xml_buffer, processStepGeneral.xsi_nil xml_boolean, backgroundMap.nilReason xml_buffer, backgroundMap.xsi_nil xml_boolean, backgroundMap.BackgroundMapValue.backgroundMapDate xml_datetime, backgroundMap.BackgroundMapValue.backgroundMapReference xml_buffer, backgroundMap.BackgroundMapValue.backgroudMapURI xml_buffer, backgroundMap.BackgroundMapValue.backgroudMapURI.nilReason xml_buffer, backgroundMap.BackgroundMapValue.backgroudMapURI.xsi_nil xml_boolean, beginLifespanVersion xml_datetime, beginLifespanVersion.nilReason xml_buffer, beginLifespanVersion.xsi_nil xml_boolean, dimensioningIndication{}.nilReason xml_buffer, dimensioningIndication{}.xsi_nil xml_boolean, dimensioningIndication{}.DimensioningIndicationMeasureValue.indicationReference xml_buffer, dimensioningIndication{}.DimensioningIndicationMeasureValue.value xml_real64, dimensioningIndication{}.DimensioningIndicationMeasureValue.value.uom xml_buffer, dimensioningIndication{}.DimensioningIndicationRealValue.indicationReference xml_buffer, dimensioningIndication{}.DimensioningIndicationRealValue.value xml_real64, dimensioningIndication{}.DimensioningIndicationIntegerValue.indicationReference xml_buffer,
      dimensioningIndication{}.DimensioningIndicationIntegerValue.value xml_int64, dimensioningIndication{}.DimensioningIndicationCharacterValue.indicationReference xml_buffer, dimensioningIndication{}.DimensioningIndicationCharacterValue.value xml_buffer, dimensioningIndication{}.DimensioningIndicationValue.indicationReference xml_buffer, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, geometry xml_geometry, inheritedFromOtherPlans xml_boolean, inheritedFromOtherPlans.nilReason xml_buffer, inheritedFromOtherPlans.xsi_nil xml_boolean, specificRegulationNature xml_buffer, specificRegulationNature.nilReason xml_buffer, specificRegulationNature.xsi_nil xml_boolean, name{} xml_buffer, name{}.nilReason xml_buffer, name{}.xsi_nil xml_boolean, regulationNature.owns xml_boolean, regulationNature.nilReason xml_buffer, regulationNature.gml_remoteSchema xml_buffer, regulationNature.xlink_href xml_buffer, regulationNature.xlink_title xml_buffer, supplementaryRegulation{}.owns xml_boolean, supplementaryRegulation{}.nilReason xml_buffer, supplementaryRegulation{}.gml_remoteSchema xml_buffer,
      supplementaryRegulation{}.xlink_href xml_buffer, supplementaryRegulation{}.xlink_title xml_buffer, officialDocument{}.owns xml_boolean, officialDocument{}.nilReason xml_buffer, officialDocument{}.gml_remoteSchema xml_buffer, officialDocument{}.xlink_href xml_buffer, officialDocument{}.xlink_title xml_buffer, officialDocument{}.xsi_nil xml_boolean, plan.owns xml_boolean, plan.nilReason xml_buffer, plan.gml_remoteSchema xml_buffer, plan.xlink_href xml_buffer, plan.xlink_title xml_buffer

Bookmark: merge gml_id BP_PLAN
AttributeRemover_6
    REMOVE_ATTRS = _result_genehmigungsDatum,_result_versionBauNVOText,_result_nummer,_result_ausfertigungsDatum,_result_gehoertZuBP_Bereich,_result_raeumlicherGeltungsbereich,_result_versionBauGB,_result_name,_result_rechtsstand,_result_aenderungenBisDatum,_result_veraenderungssperreDatum,_result_versionBauNVO,_result_untergangsDatum,_result_technHerstellDatum,_result_satzungsbeschlussDatum,_result_aufstellungsbeschlussDatum,_result_rasterBasis,_result_inkrafttretensDatum,_result_rechtsverordnungsDatum,_result_versionBauGBText
    LIST_ATTRS = _list_member{} _list_member{}.gml_id _list_restriction{} _list_restriction{}.gml_id _results_list_auslegungsEndDatum{} _results_list_auslegungsStartDatum{} _results_list_begruendungstexte{} _results_list_bereich{} _results_list_hatGenerAttribut{} _results_list_inhaltBPlan{} _results_list_planArt{} _results_list_texte{} _results_list_traegerbeteiligungsEndDatum{} _results_list_traegerbeteiligungsStartDatum{} officialDocument{}.xlink_href
    -> AttributeRenamer
AttributeRenamer
    ATTR_TABLE = RENAME_SET_DEFAULT gml_id > gml_id_plan
    -> FeatureMerger_4 [SUPPLIER]
FeatureMerger_4
    REJECT_NULL_MISSING_KEYS = No
    JOIN_KEYS = @Value(_result_gehoertZuBP_Bereich) #@Value(gml_id_BP_Bereich) AUTO
    ATTR_CONFLICT_RES = Use Requestor
    MERGE_TYPE = Attributes Only
    IGNORE_NULLS = No
    PROCESS_DUPS = No
    SUPPLIERS_FIRST = No
    ATTR_ACCUM_MODE = Merge Supplier
    MERGED -> AttributeSplitter

Bookmark: merge gml_id BP_PLAN
AttributeRemover_4
    REMOVE_ATTRS = _result_genehmigungsDatum,_result_versionBauNVOText,_result_nummer,_result_ausfertigungsDatum,_result_gehoertZuBP_Bereich,_result_raeumlicherGeltungsbereich,_result_versionBauGB,_result_name,_result_rechtsstand,_result_aenderungenBisDatum,_result_veraenderungssperreDatum,_result_versionBauNVO,_result_untergangsDatum,_result_technHerstellDatum,_result_satzungsbeschlussDatum,_result_aufstellungsbeschlussDatum,_result_rasterBasis,_result_inkrafttretensDatum,_result_rechtsverordnungsDatum,_result_versionBauGBText
    LIST_ATTRS = _list_member{} _list_member{}.gml_id _list_restriction{} _list_restriction{}.gml_id _results_list_auslegungsEndDatum{} _results_list_auslegungsStartDatum{} _results_list_begruendungstexte{} _results_list_bereich{} _results_list_hatGenerAttribut{} _results_list_inhaltBPlan{} _results_list_planArt{} _results_list_texte{} _results_list_traegerbeteiligungsEndDatum{} _results_list_traegerbeteiligungsStartDatum{} officialDocument{}.xlink_href
    -> AttributeRenamer_2
AttributeRenamer_2
    ATTR_TABLE = RENAME_SET_DEFAULT gml_id > gml_id_plan
    -> FeatureMerger_5 [SUPPLIER]
FeatureMerger_5
    REJECT_NULL_MISSING_KEYS = No
    JOIN_KEYS = @Value(_result_gehoertZuBP_Bereich) #@Value(gml_id_BP_Bereich) AUTO
    ATTR_CONFLICT_RES = Use Requestor
    MERGE_TYPE = Attributes Only
    IGNORE_NULLS = No
    PROCESS_DUPS = No
    SUPPLIERS_FIRST = No
    ATTR_ACCUM_MODE = Merge Supplier
    MERGED -> AttributeSplitter_3

Bookmark: PLU:ZoningElement
X2I_ZoningElement_extract
    GML_ID = @Value(gml_id)
    _XML_OUTPUT = @Value(_xml_output)
    X2I_ZoningElement_extract_Output -> FeatureMerger_4 [REQUESTOR]
AttributeSplitter
    ATTR_NAME = gml_id
    TRIM_OPTION = Both
    DELIMITER = _
    DROP_EMPTY_PARTS = No
    LIST_NAME = _list_hilucs_key
    -> PythonCaller_createOfficialDocumentList_2
PythonCaller_createOfficialDocumentList_2
    PYTHONSOURCE:
      import fme
      import fmeobjects

      def createOfficialDocumentList(feature):
          listTexte = feature.getAttribute("_results_list_refTextInhalt{}")
          listBegruendung = feature.getAttribute("_results_list_refBegruendungInhalt{}")
          listDocuments = []

          if listTexte:
              for i in range(len(listTexte)):
                  listDocuments.append(listTexte[i])

          if listBegruendung:
              for j in range(len(listBegruendung)):
                  listDocuments.append(listBegruendung[j])

          if listDocuments:
              for k in range(len(listDocuments)):
                  attrName = "officialDocument{" + str(k) + "}" + ".xlink_href"
                  feature.setAttribute(attrName,listDocuments[k])
    NEW_ATTRIBUTES = officialDocument{}.xlink_href
    PYTHONSYMBOL = createOfficialDocumentList
    -> PythonCaller_createOfficialDocumentSqlStatement_2
    -> Tester_zweckbestimmung
PythonCaller_createOfficialDocumentSqlStatement_2
    PYTHONSOURCE:
      import fme
      import fmeobjects

      def createOfficialDocumentSqlStatement(feature):
          listTexte = feature.getAttribute("_results_list_refTextInhalt{}")
          listBegruendung = feature.getAttribute("_results_list_refBegruendungInhalt{}")
          listDocuments = []

          sqlStrDocum = "SELECT gml_id, ft_type, binary_object FROM xplan41.gml_objects WHERE gml_id LIKE '"
          sqlStrOr = "' OR gml_id LIKE '"
          sqlStrEnd = "';"

          if listTexte:
              for i in range(len(listTexte)):
                  listDocuments.append(listTexte[i])

          if listBegruendung:
              for j in range(len(listBegruendung)):
                  listDocuments.append(listBegruendung[j])

          if listDocuments:
              for k in range(len(listDocuments)):
                  if k == 0:
                      docRef = listDocuments[k].replace("#", "")
                      sqlStrDocum += docRef
                  else:
                      sqlStrDocum += sqlStrOr
                      docRef = listDocuments[k].replace("#", "")
                      sqlStrDocum += docRef

              sqlStrDocum += sqlStrEnd
              feature.setAttribute("sqlStrStatementOfficialDocument",sqlStrDocum)
    NEW_ATTRIBUTES = sqlStrStatementOfficialDocument
    PYTHONSYMBOL = createOfficialDocumentSqlStatement
    -> Tester_20
Note: if zweckbestimmung has value
Tester_zweckbestimmung
    BOOL_OP = OR
    TEST_MODE = Automatic
    TEST_CLAUSE = TEST @Value(_result_zweckbestimmung) ATTRIBUTE_HAS_VALUE ""
    TEST_DESCRIPTION = ""
    PASSED -> PythonCaller_findInCodeList
    FAILED -> Tester_nutzungsform
PythonCaller_findInCodeList
    PYTHONSOURCE:
      import fme
      import fmeobjects

      def findInCodeList(feature):
          listHilucsKey = feature.getAttribute("_list_hilucs_key{}")
          strCode = feature.getAttribute('_result_zweckbestimmung')
          strKey = ""
          findCode = False

          if listHilucsKey:
              strKey = listHilucsKey[1] + "_" + listHilucsKey[2] + "_zweckbestimmung_" + strCode

              readerBp = open("codes/BP_Plan_Values_hilucsLandUse_formatiert.csv", "r")
              for line in readerBp:
                  spalten = line.split(";")
                  readerKey = spalten[0]

                  if strKey == readerKey:
                      findCode = True
                      break

              if findCode == False:
                  readerSo = open("codes/SO_Plan_Values_hilucsLandUse_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_3
Tester_3
    BOOL_OP = OR
    TEST_MODE = Automatic
    TEST_CLAUSE = TEST @Value(_findInCodeList) = Yes
    TEST_DESCRIPTION = ""
    PASSED -> AttributeCreator_5
    FAILED -> Tester_nutzungsform
AttributeCreator_5
    ATTR_TABLE = SET_TO _hilucs_key = @Value(_list_hilucs_key{1})_@Value(_list_hilucs_key{2})_zweckbestimmung_@Value(_result_zweckbestimmung)
    -> AttributeValueMapper_6
Note: if nutzungsform has value
Tester_nutzungsform
    BOOL_OP = OR
    TEST_MODE = Automatic
    TEST_CLAUSE = TEST @Value(_result_nutzungsform) ATTRIBUTE_HAS_VALUE ""
    TEST_DESCRIPTION = ""
    PASSED -> PythonCaller_findInCodeList_2
    FAILED -> Tester_ziel
PythonCaller_findInCodeList_2
    PYTHONSOURCE:
      import fme
      import fmeobjects

      def findInCodeList(feature):
          listHilucsKey = feature.getAttribute("_list_hilucs_key{}")
          strCode = feature.getAttribute('_result_nutzungsform')
          strKey = ""
          findCode = False

          if listHilucsKey:
              strKey = listHilucsKey[1] + "_" + listHilucsKey[2] + "_nutzungsform_" + strCode

              readerBp = open("codes/BP_Plan_Values_hilucsLandUse_formatiert.csv", "r")
              for line in readerBp:
                  spalten = line.split(";")
                  readerKey = spalten[0]

                  if strKey == readerKey:
                      findCode = True
                      break

              if findCode == False:
                  readerSo = open("codes/SO_Plan_Values_hilucsLandUse_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_4
Tester_4
    BOOL_OP = OR
    TEST_MODE = Automatic
    TEST_CLAUSE = TEST @Value(_findInCodeList) = Yes
    TEST_DESCRIPTION = ""
    PASSED -> AttributeCreator_6
    FAILED -> Tester_ziel
AttributeCreator_6
    ATTR_TABLE = SET_TO _hilucs_key = @Value(_list_hilucs_key{1})_@Value(_list_hilucs_key{2})_nutzungsform_@Value(_result_nutzungsform)
    -> AttributeValueMapper_6
Note: if ziel has value
Tester_ziel
    BOOL_OP = OR
    TEST_MODE = Automatic
    TEST_CLAUSE = TEST @Value(_result_ziel) ATTRIBUTE_HAS_VALUE ""
    TEST_DESCRIPTION = ""
    PASSED -> PythonCaller_findInCodeList_3
    FAILED -> Tester_besondereArtDerBaulNutzung
PythonCaller_findInCodeList_3
    PYTHONSOURCE:
      import fme
      import fmeobjects

      def findInCodeList(feature):
          listHilucsKey = feature.getAttribute("_list_hilucs_key{}")
          strCode = feature.getAttribute('_result_ziel')
          strKey = ""
          findCode = False

          if listHilucsKey:
              strKey = listHilucsKey[1] + "_" + listHilucsKey[2] + "_ziel_" + strCode

              readerBp = open("codes/BP_Plan_Values_hilucsLandUse_formatiert.csv", "r")
              for line in readerBp:
                  spalten = line.split(";")
                  readerKey = spalten[0]

                  if strKey == readerKey:
                      findCode = True
                      break

              if findCode == False:
                  readerSo = open("codes/SO_Plan_Values_hilucsLandUse_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_5
Tester_5
    BOOL_OP = OR
    TEST_MODE = Automatic
    TEST_CLAUSE = TEST @Value(_findInCodeList) = Yes
    TEST_DESCRIPTION = ""
    PASSED -> AttributeCreator_7
    FAILED -> Tester_besondereArtDerBaulNutzung
AttributeCreator_7
    ATTR_TABLE = SET_TO _hilucs_key = @Value(_list_hilucs_key{1})_@Value(_list_hilucs_key{2})_ziel_@Value(_result_ziel)
    -> AttributeValueMapper_6
Note: if besondereArtDerBaulNutzung has value
Tester_besondereArtDerBaulNutzung
    BOOL_OP = OR
    TEST_MODE = Automatic
    TEST_CLAUSE = TEST @Value(_result_besondereArtDerBaulNutzung) ATTRIBUTE_HAS_VALUE ""
    TEST_DESCRIPTION = ""
    PASSED -> PythonCaller_findInCodeList_4
    FAILED -> Tester_allgArtDerBaulNutzung
PythonCaller_findInCodeList_4
    PYTHONSOURCE:
      import fme
      import fmeobjects

      def findInCodeList(feature):
          listHilucsKey = feature.getAttribute("_list_hilucs_key{}")
          strCode = feature.getAttribute('_result_besondereArtDerBaulNutzung')
          strKey = ""
          findCode = False

          if listHilucsKey:
              strKey = listHilucsKey[1] + "_" + listHilucsKey[2] + "_besondereArtDerBaulNutzung_" + strCode

              readerBp = open("codes/BP_Plan_Values_hilucsLandUse_formatiert.csv", "r")
              for line in readerBp:
                  spalten = line.split(";")
                  readerKey = spalten[0]

                  if strKey == readerKey:
                      findCode = True
                      break

              if findCode == False:
                  readerSo = open("codes/SO_Plan_Values_hilucsLandUse_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_6
Tester_6
    BOOL_OP = OR
    TEST_MODE = Automatic
    TEST_CLAUSE = TEST @Value(_findInCodeList) = Yes
    TEST_DESCRIPTION = ""
    PASSED -> AttributeCreator_8
    FAILED -> Tester_allgArtDerBaulNutzung
AttributeCreator_8
    ATTR_TABLE = SET_TO _hilucs_key = @Value(_list_hilucs_key{1})_@Value(_list_hilucs_key{2})_besondereArtDerBaulNutzung_@Value(_result_besondereArtDerBaulNutzung)
    -> AttributeValueMapper_6
Note: if allgArtDerBaulNutzung has value / ! hat keinen HILUCS-Eintrag!
Tester_allgArtDerBaulNutzung
    BOOL_OP = OR
    TEST_MODE = Automatic
    TEST_CLAUSE = TEST @Value(_result_allgArtDerBaulNutzung) ATTRIBUTE_HAS_VALUE ""
    TEST_DESCRIPTION = ""
    PASSED -> PythonCaller_findInCodeList_5
    FAILED -> AttributeCreator_24
PythonCaller_findInCodeList_5
    PYTHONSOURCE:
      import fme
      import fmeobjects

      def findInCodeList(feature):
          listHilucsKey = feature.getAttribute("_list_hilucs_key{}")
          strCode = feature.getAttribute('_result_allgArtDerBaulNutzung')
          strKey = ""
          findCode = False

          if listHilucsKey:
              strKey = listHilucsKey[1] + "_" + listHilucsKey[2] + "_allgArtDerBaulNutzung_" + strCode

              readerBp = open("codes/BP_Plan_Values_hilucsLandUse_formatiert.csv", "r")
              for line in readerBp:
                  spalten = line.split(";")
                  readerKey = spalten[0]

                  if strKey == readerKey:
                      findCode = True
                      break

              if findCode == False:
                  readerSo = open("codes/SO_Plan_Values_hilucsLandUse_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_7
Tester_7
    BOOL_OP = OR
    TEST_MODE = Automatic
    TEST_CLAUSE = TEST @Value(_findInCodeList) = Yes
    TEST_DESCRIPTION = ""
    PASSED -> AttributeCreator_9
    FAILED -> AttributeCreator_24
AttributeCreator_9
    ATTR_TABLE = SET_TO _hilucs_key = @Value(_list_hilucs_key{1})_@Value(_list_hilucs_key{2})_allgArtDerBaulNutzung_@Value(_result_allgArtDerBaulNutzung)
    -> AttributeValueMapper_6
AttributeCreator_24
    ATTR_TABLE = SET_TO _hilucs_key = @Value(_list_hilucs_key{1})_@Value(_list_hilucs_key{2})__
    -> AttributeValueMapper_6
AttributeValueMapper_6
    SRC = _hilucs_key
    VAL_ATTR = _hilucs_value
    LUT =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
    DIRECTION = Forward (Source To Destination)
    -> AttributeValueMapper_7
AttributeValueMapper_7
    SRC = _hilucs_key
    VAL_ATTR = _specificLandUse_value
    LUT =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
    DIRECTION = Forward (Source To Destination)
    -> AttributeValueMapper_4
AttributeValueMapper_4
    SRC = _result_rechtsstand
    VAL_ATTR = _SpatialPlan.processStepGeneral
    LUT = 1000,elaboration,2000,elaboration,2100,elaboration,2200,elaboration,2300,elaboration,2400,elaboration,3000,adoption,4000,legalForce,4500,obsolete,5000,obsolete
    DIRECTION = Forward (Source To Destination)
    -> AttributeValueMapper_5
AttributeValueMapper_5
    SRC = _result_rechtscharakter
    VAL_ATTR = _regulationNature
    LUT = 1000,generallyBinding,2000,generallyBinding,3000,nonBinding,4000,definedInLegislation,5000,definedInLegislation,9998,nonBinding
    DIRECTION = Forward (Source To Destination)
    -> Tester
Tester
    BOOL_OP = OR
    TEST_MODE = Automatic
    TEST_CLAUSE:
      TEST @Value(_hilucs_value) NOT_ATTRIBUTE_HAS_VALUE ""
      TEST _hilucs_value ATTRIBUTE_IS_MISSING ""
      TEST _hilucs_value ATTRIBUTE_VALUE_NULL ""
      TEST _hilucs_value ATTRIBUTE_IS_EMPTY ""
    TEST_DESCRIPTION = ""
    PASSED -> AttributeCreator_27
    FAILED -> AttributeSplitter_2
AttributeCreator_27
    ATTR_TABLE:
      SET_TO _hilucs_value = error
      SET_TO _specificLandUse_value = error
    -> AttributeSplitter_2
AttributeSplitter_2
    ATTR_NAME = _hilucs_value
    TRIM_OPTION = Both
    DELIMITER = &&
    DROP_EMPTY_PARTS = No
    LIST_NAME = _hilucs_values_list
    -> PythonCaller_6
PythonCaller_6
    PYTHONSOURCE:
      import fme
      import fmeobjects

      def setHilucsValues(feature):
          listHilucsValues = feature.getAttribute("_hilucs_values_list{}")

          if listHilucsValues:
              for i in range(len(listHilucsValues)):
                  if listHilucsValues[i]:
                      attrName = "hilucsLandUse{" + str(i) + "}" + ".xlink_href"
                      strHilucs = "http://inspire.ec.europa.eu/codelist/HILUCSValue/" + listHilucsValues[i]
                      feature.setAttribute(attrName,strHilucs)
    PYTHONSYMBOL = setHilucsValues
    -> PythonCaller_dimensions_2
PythonCaller_dimensions_2
    PYTHONSOURCE:
      # -*- coding: UTF-8 -*-
      import fme
      import fmeobjects
      import xml.etree.ElementTree as ET

      def setDimensionsValues(feature):
          strXml = feature.getAttribute("_result_hoehenangabe")
          strXmlEncode = strXml.encode(encoding='UTF-8')
          root = ET.fromstring(strXmlEncode)

          hoehenbezug = {"absolutNHM": 1000, "relativGelaendeoberkante": 2000, "relativGehwegOberkante": 2500, "relativBezugshoehe": 3000}
          bezugspunkt = {"TH": 1000, "FH": 2000, "OK": 3000, "LH": 3500, "SH": 4000, "EFH": 4500, "HBA": 5000, "UK": 5500, "GBH": 6000}
          countElements = -1

          for element in root.iter('out'):
              countElements += 1
              indicationReference = ""
              value = ""

              hoehenbereich = False
              tmpIndicationReference = ""
              indicationReference2 = ""
              value2 = ""

              if len(list(element)) > 0:
                  for i in range(len(list(element))):
                      if element[i].tag == '{http://www.xplanung.de/xplangml/4/1}hoehenbezug':
                          for dictKey, dictValue in hoehenbezug.items():
                              if element[i].text == str(dictValue):
                                  indicationReference += dictKey
                                  break
                      elif element[i].tag == '{http://www.xplanung.de/xplangml/4/1}abweichenderHoehenbezug':
                          indicationReference += element[i].text
                      elif element[i].tag == '{http://www.xplanung.de/xplangml/4/1}bezugspunkt':
                          for dictKey, dictValue in bezugspunkt.items():
                              if element[i].text == str(dictValue):
                                  indicationReference += "_" + dictKey
                                  break
                      elif element[i].tag == '{http://www.xplanung.de/xplangml/4/1}abweichenderBezugspunkt':
                          indicationReference += "_" + element[i].text
                      elif element[i].tag == '{http://www.xplanung.de/xplangml/4/1}h' or element[i].tag == '{http://www.xplanung.de/xplangml/4/1}hZwingend':
                          indicationReference += "_" + element[i].tag.replace("{http://www.xplanung.de/xplangml/4/1}", "")
                          value = float(element[i].text)
                      elif element[i].tag == '{http://www.xplanung.de/xplangml/4/1}hMin' or element[i].tag == '{http://www.xplanung.de/xplangml/4/1}hMax':
                          if hoehenbereich == False:
                              tmpIndicationReference = indicationReference
                              indicationReference += "_" + element[i].tag.replace("{http://www.xplanung.de/xplangml/4/1}", "")
                              value = float(element[i].text)
                              hoehenbereich = True
                          else:
                              indicationReference2 += tmpIndicationReference
                              indicationReference2 += "_" + element[i].tag.replace("{http://www.xplanung.de/xplangml/4/1}", "")
                              value2 = float(element[i].text)

              attrNameRef = "dimensioningIndication{" + str(countElements) + "}" + ".DimensioningIndicationMeasureValue.indicationReference"
              attrNameVal = "dimensioningIndication{" + str(countElements) + "}" + ".DimensioningIndicationMeasureValue.value"
              attrNameUom = "dimensioningIndication{" + str(countElements) + "}" + ".DimensioningIndicationMeasureValue.value.uom"
              feature.setAttribute(attrNameRef,indicationReference)
              feature.setAttribute(attrNameVal,str(value))
              feature.setAttribute(attrNameUom,"m")

              if hoehenbereich == True and indicationReference2 != "" and value2 != "":
                  countElements += 1
                  attrNameRef = "dimensioningIndication{" + str(countElements) + "}" + ".DimensioningIndicationMeasureValue.indicationReference"
                  attrNameVal = "dimensioningIndication{" + str(countElements) + "}" + ".DimensioningIndicationMeasureValue.value"
                  attrNameUom = "dimensioningIndication{" + str(countElements) + "}" + ".DimensioningIndicationMeasureValue.value.uom"
                  feature.setAttribute(attrNameRef,indicationReference2)
                  feature.setAttribute(attrNameVal,str(value2))
                  feature.setAttribute(attrNameUom,"m")

          feature.setAttribute("dimensCount1",countElements)
    NEW_ATTRIBUTES = dimensCount1
    PYTHONSYMBOL = setDimensionsValues
    -> PythonCaller_dimensions_4
PythonCaller_dimensions_4
    PYTHONSOURCE:
      # -*- coding: UTF-8 -*-
      import fme
      import fmeobjects
      import xml.etree.ElementTree as ET

      def setDimensionsValues(feature):
          strXml = feature.getAttribute('_result_spezielleAttribute')
          strXmlEncode = strXml.encode(encoding='UTF-8')
          root = ET.fromstring(strXmlEncode)

          dictType = {"MaxAnzahlWohnungen": "Integer","Zmin": "Integer","Zmax": "Integer","Zzwingend": "Integer","Z": "Integer","Z_Ausn": "Integer","Z_Staffel": "Integer","Z_Dach": "Integer","ZUmin": "Integer","ZUmax": "Integer","ZUzwingend": "Integer","ZU": "Integer","ZU_Ausn": "Integer","GFZmin": "Real","GFZmax": "Real","GFZ": "Real","GFZ_Ausn": "Real","BMZ": "Real","BMZ_Ausn": "Real","GRZ": "Real","GRZmin": "Real","GRZmax": "Real","GRZ_Ausn": "Real","Fmin": "Measure","Fmax": "Measure","Bmin": "Measure","Bmax": "Measure","Tmin": "Measure","Tmax": "Measure","GFmin": "Measure","GFmax": "Measure","GF": "Measure","GF_Ausn": "Measure","BM": "Measure","BM_Ausn": "Measure","GRmin": "Measure","GRmax": "Measure","GR": "Measure","GR_Ausn": "Measure","DNmin": "Measure","DNmax": "Measure","DN": "Measure","DNZwingend": "Measure","FR": "Measure","dachform": "dictDachform","ZWohn": "Integer","GFAntWohnen": "Measure","GFWohnen": "Measure","GFAntGewerbe": "Measure","GFGewerbe": "Measure","wohnnutzungEGStrasse": "dictWohnnutzungEGStrasse","bauweise": "dictBauweise","bebauungsArt": "dictBebauungsArt"}
          dictDachform = {"Flachdach": 1000, "Pultdach": 2100, "VersetztesPultdach": 2200, "Satteldach": 3100, "Walmdach": 3200, "Krueppelwalmdach": 3300, "Mansardendach": 3400, "Zeltdach": 3500, "Kegeldach": 3600, "Kuppeldach": 3700, "Sheddach": 3800, "Bogendach": 3900, "Turmdach": 4000, "Mischform": 5000, "Sonstiges": 9999}
          dictWohnnutzungEGStrasse = {"Zulaessig": 1000, "NichtZulaessig": 2000, "Ausnahmsweise": 3000}
          dictBauweise = {"OffeneBauweise": 1000, "Geschlossene": 2000, "Abweichende": 3000}
          dictBebauungsArt = {"Einzelhaeuser": 1000, "Doppelhaeuser": 2000, "Hausgruppen": 3000, "EinzelDoppelhaeuser": 4000, "Einzelhaeuser": 5000, "Doppelhaeuser": 6000, "Reihenhaeuser": 7000}
          dictMeasure = {"Fmin": "m2","Fmax": "m2","Bmin": "m","Bmax": "m","Tmin": "m","Tmax": "m","GFmin": "m2","GFmax": "m2","GF": "m2","GF_Ausn": "m2","BM": "m3","BM_Ausn": "m3","GRmin": "m2","GRmax": "m2","GR": "m2","GR_Ausn": "m2","DNmin": "deg","DNmax": "deg","DN": "deg","DNZwingend": "deg","FR": "deg","GFAntWohnen": "scale","GFWohnen": "m2","GFAntGewerbe": "scale","GFGewerbe": "m2"}

          countElements = feature.getAttribute('dimensCount1')

          for element in root.iter('out'):
              if len(list(element)) > 0:
                  for i in range(len(list(element))):
                      indicationReference = ""
                      value = ""
                      uom = ""
                      typ = ""

                      countElements += 1
                      tag = element[i].tag.replace("{http://www.xplanung.de/xplangml/4/1}", "")

                      for dictKeyType, dictValueType in dictType.items():
                          if tag == dictKeyType:
                              if dictValueType == "Integer":
                                  indicationReference = tag
                                  value = int(element[i].text)
                                  typ = "Integer"
                                  break
                              elif dictValueType == "Real":
                                  indicationReference = tag
                                  value = float(element[i].text)
                                  typ = "Real"
                                  break
                              elif dictValueType == "Measure":
                                  for dictKeyMeasure, dictValueMeasure in dictMeasure.items():
                                      if tag == dictKeyMeasure:
                                          indicationReference = tag
                                          value = float(element[i].text)
                                          typ = "Measure"
                                          uom = dictValueMeasure
                                          break
                              elif dictValueType == "dictDachform":
                                  for dictKeyDachform, dictValueDachform in dictDachform.items():
                                      if int(element[i].text) == int(dictValueDachform):
                                          indicationReference = "Dachform"
                                          value = dictKeyDachform
                                          typ = "Character"
                                          break
                              elif dictValueType == "dictWohnnutzungEGStrasse":
                                  for dictKeyWohnnutzungEGStrasse, dictValueWohnnutzungEGStrasse in dictWohnnutzungEGStrasse.items():
                                      if int(element[i].text) == int(dictValueWohnnutzungEGStrasse):
                                          indicationReference = "wohnnutzungEGStrasse"
                                          value = dictKeyWohnnutzungEGStrasse
                                          typ = "Character"
                                          break
                              elif dictValueType == "dictBauweise":
                                  for dictKeyBauweise, dictValueBauweise in dictBauweise.items():
                                      if int(element[i].text) == int(dictValueBauweise):
                                          indicationReference = "Bauweise"
                                          value = dictKeyBauweise
                                          typ = "Character"
                                          break
                              elif dictValueType == "dictBebauungsArt":
                                  for dictKeyBebauungsArt, dictValueBebauungsArt in dictBebauungsArt.items():
                                      if int(element[i].text) == int(dictValueBebauungsArt):
                                          indicationReference = "BebauungsArt"
                                          value = dictKeyBebauungsArt
                                          typ = "Character"
                                          break

                      if typ == "Integer":
                          attrNameRef = "dimensioningIndication{" + str(countElements) + "}" + ".DimensioningIndicationIntegerValue.indicationReference"
                          attrNameVal = "dimensioningIndication{" + str(countElements) + "}" + ".DimensioningIndicationIntegerValue.value"
                          feature.setAttribute(attrNameRef,indicationReference)
                          feature.setAttribute(attrNameVal,str(value))
                      elif typ == "Real":
                          attrNameRef = "dimensioningIndication{" + str(countElements) + "}" + ".DimensioningIndicationRealValue.indicationReference"
                          attrNameVal = "dimensioningIndication{" + str(countElements) + "}" + ".DimensioningIndicationRealValue.value"
                          feature.setAttribute(attrNameRef,indicationReference)
                          feature.setAttribute(attrNameVal,str(value))
                      elif typ == "Measure":
                          attrNameRef = "dimensioningIndication{" + str(countElements) + "}" + ".DimensioningIndicationMeasureValue.indicationReference"
                          attrNameVal = "dimensioningIndication{" + str(countElements) + "}" + ".DimensioningIndicationMeasureValue.value"
                          attrNameUom = "dimensioningIndication{" + str(countElements) + "}" + ".DimensioningIndicationMeasureValue.value.uom"
                          feature.setAttribute(attrNameRef,indicationReference)
                          feature.setAttribute(attrNameVal,str(value))
                          feature.setAttribute(attrNameUom,uom)
                      elif typ == "Character":
                          attrNameRef = "dimensioningIndication{" + str(countElements) + "}" + ".DimensioningIndicationCharacterValue.indicationReference"
                          attrNameVal = "dimensioningIndication{" + str(countElements) + "}" + ".DimensioningIndicationCharacterValue.value"
                          feature.setAttribute(attrNameRef,indicationReference)
                          feature.setAttribute(attrNameVal,value)
    PYTHONSYMBOL = setDimensionsValues
    -> AttributeCreator_4
Note: optionales Zielattribut für das optionale xplan-Attribute "hatGenerAttribut" wegelassen!
AttributeCreator_4
    ATTR_TABLE:
      SET_TO gml_id = @Value(gml_id)
      SET_TO gml_identifier.codeSpace = http://inspire.ec.europa.eu/ids
      SET_TO gml_identifier = https://registry.gdi-de.org/id/de.hh/0a2b2809-dd93-45e6-bc0e-26093eb1122a/@Value(gml_id)
      SET_TO inspireId.Identifier.localId = @Value(gml_id)
      SET_TO inspireId.Identifier.namespace = https://registry.gdi-de.org/id/de.hh/0a2b2809-dd93-45e6-bc0e-26093eb1122a
      SET_TO beginLifespanVersion.nilReason = other:unpopulated
      SET_TO beginLifespanVersion.xsi_nil = true
      SET_TO endLifespanVersion.nilReason = other:unpopulated
      SET_TO endLifespanVersion.xsi_nil = true
      SET_TO _hilucsLandUse{0}.xlink_href = _Info: http://inspire.ec.europa.eu/codelist/HILUCSValue/
      SET_TO _hilucsLandUse{0}.nilReason = FME_CONDITIONAL:DEFAULT_VALUE'_FME_NO_OP_'BOOL_OP;OR;COMPOSITE_TEST;<Unused>;TEST _hilucs_value ATTRIBUTE_IS_MISSING _FME_BLANK_STRING_'other:unpopulated'FME_NUM_CONDITIONS2___
      SET_TO _hilucsLandUse{0}.xsi_nil = FME_CONDITIONAL:DEFAULT_VALUE'_FME_NO_OP_'BOOL_OP;OR;COMPOSITE_TEST;<Unused>;TEST _hilucs_value ATTRIBUTE_IS_MISSING _FME_BLANK_STRING_'true'FME_NUM_CONDITIONS2___
      SET_TO hilucsPresence.nilReason = other:unpopulated
      SET_TO hilucsPresence.xsi_nil = true
      SET_TO specificLandUse{0}.xlink_href = FME_CONDITIONAL:DEFAULT_VALUE'_FME_NO_OP_'BOOL_OP;OR;COMPOSITE_TEST;<Unused>;TEST _specificLandUse_value NOT_ATTRIBUTE_IS_MISSING _FME_BLANK_STRING_'http://daten-hamburg.de/inspire/codelist/LandUseClassificationValue_Extension.xml#@Value(_specificLandUse_value)'FME_NUM_CONDITIONS2___
      SET_TO specificLandUse{0}.nilReason = FME_CONDITIONAL:DEFAULT_VALUE'_FME_NO_OP_'BOOL_OP;OR;COMPOSITE_TEST;<Unused>;TEST _specificLandUse_value ATTRIBUTE_IS_MISSING _FME_BLANK_STRING_'other:unpopulated'FME_NUM_CONDITIONS2___
      SET_TO specificLandUse{0}.xsi_nil = FME_CONDITIONAL:DEFAULT_VALUE'_FME_NO_OP_'BOOL_OP;OR;COMPOSITE_TEST;<Unused>;TEST _specificLandUse_value ATTRIBUTE_IS_MISSING _FME_BLANK_STRING_'true'FME_NUM_CONDITIONS2___
      SET_TO specificPresence.nilReason = other:unpopulated
      SET_TO specificPresence.xsi_nil = true
      SET_TO regulationNature.xlink_href = FME_CONDITIONAL:DEFAULT_VALUE'http://inspire.ec.europa.eu/codelist/RegulationNatureValue/default'BOOL_OP;OR;COMPOSITE_TEST;<Unused>;TEST _result_rechtscharakter NOT_ATTRIBUTE_IS_MISSING _FME_BLANK_STRING_'http://inspire.ec.europa.eu/codelist/RegulationNatureValue/@Value(_regulationNature)'FME_NUM_CONDITIONS2___
      SET_TO _regulationNature.nilReason = FME_CONDITIONAL:DEFAULT_VALUE'_FME_NO_OP_'BOOL_OP;OR;COMPOSITE_TEST;<Unused>;TEST _result_rechtscharakter ATTRIBUTE_IS_MISSING _FME_BLANK_STRING_'other:unpopulated'FME_NUM_CONDITIONS2___
      SET_TO _regulationNature.xsi_nil = FME_CONDITIONAL:DEFAULT_VALUE'_FME_NO_OP_'BOOL_OP;OR;COMPOSITE_TEST;<Unused>;TEST _result_rechtscharakter ATTRIBUTE_IS_MISSING _FME_BLANK_STRING_'true'FME_NUM_CONDITIONS2___
      SET_TO processStepGeneral.xlink_href = FME_CONDITIONAL:DEFAULT_VALUE'_FME_NO_OP_'BOOL_OP;OR;COMPOSITE_TEST;<Unused>;TEST _result_rechtsstand NOT_ATTRIBUTE_IS_MISSING _FME_BLANK_STRING_'http://inspire.ec.europa.eu/codelist/ProcessStepGeneralValue/@Value(_SpatialPlan.processStepGeneral)'FME_NUM_CONDITIONS2___
      SET_TO processStepGeneral.nilReason = FME_CONDITIONAL:DEFAULT_VALUE'_FME_NO_OP_'BOOL_OP;OR;COMPOSITE_TEST;<Unused>;TEST _result_rechtsstand ATTRIBUTE_IS_MISSING _FME_BLANK_STRING_'other:unpopulated'FME_NUM_CONDITIONS2___
      SET_TO processStepGeneral.xsi_nil = FME_CONDITIONAL:DEFAULT_VALUE'_FME_NO_OP_'BOOL_OP;OR;COMPOSITE_TEST;<Unused>;TEST _result_rechtsstand ATTRIBUTE_IS_MISSING _FME_BLANK_STRING_'true'FME_NUM_CONDITIONS2___
      SET_TO backgroundMap.nilReason = other:unpopulated
      SET_TO backgroundMap.xsi_nil = true
      SET_TO _officialDocument{0}.xlink_href = _Info: py
      SET_TO plan.xlink_href = #@Value(gml_id_plan)
      SET_TO validFrom = FME_CONDITIONAL:DEFAULT_VALUE'_FME_NO_OP_'BOOL_OP;OR;COMPOSITE_TEST;<Unused>;TEST _result_startBedingung NOT_ATTRIBUTE_IS_MISSING _FME_BLANK_STRING_'@Value(_result_startBedingung)'FME_NUM_CONDITIONS2___
      SET_TO _validFrom.nilReason = FME_CONDITIONAL:DEFAULT_VALUE'_FME_NO_OP_'BOOL_OP;OR;COMPOSITE_TEST;<Unused>;TEST _result_startBedingung ATTRIBUTE_IS_MISSING _FME_BLANK_STRING_'other:unpopulated'FME_NUM_CONDITIONS2___
      SET_TO _validFrom.xsi_nil = FME_CONDITIONAL:DEFAULT_VALUE'_FME_NO_OP_'BOOL_OP;OR;COMPOSITE_TEST;<Unused>;TEST _result_startBedingung ATTRIBUTE_IS_MISSING _FME_BLANK_STRING_'true'FME_NUM_CONDITIONS2___
      SET_TO validTo = FME_CONDITIONAL:DEFAULT_VALUE'_FME_NO_OP_'BOOL_OP;OR;COMPOSITE_TEST;<Unused>;TEST _result_endeBedingung NOT_ATTRIBUTE_IS_MISSING _FME_BLANK_STRING_'@Value(_result_endeBedingung)'FME_NUM_CONDITIONS2___
      SET_TO _validTo.nilReason = FME_CONDITIONAL:DEFAULT_VALUE'_FME_NO_OP_'BOOL_OP;OR;COMPOSITE_TEST;<Unused>;TEST _result_endeBedingung ATTRIBUTE_IS_MISSING _FME_BLANK_STRING_'other:unpopulated'FME_NUM_CONDITIONS2___
      SET_TO _validTo.xsi_nil = FME_CONDITIONAL:DEFAULT_VALUE'_FME_NO_OP_'BOOL_OP;OR;COMPOSITE_TEST;<Unused>;TEST _result_endeBedingung ATTRIBUTE_IS_MISSING _FME_BLANK_STRING_'true'FME_NUM_CONDITIONS2___
    -> GeometryReplacer_5

Bookmark: gml geometry
GeometryReplacer_5
    KIND_LONG = GML
    SOURCE = @Value(_result_position)
    SRS_AXIS_ORDER_DISPLAY = Automatic
    REMOVE_ATTRIBUTE = Yes
    -> GeometryValidator_2
GeometryValidator_2
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    NAN_REMOVAL = NAN_REMOVAL
    SELF_INTERSECTING = SELF_INTERSECTING
    CHECK_HOLE_TOUCHING_POLYGON = No
    CONNECT_Z_MODE_TR = First Wins
    SUMMARY = Detailed
    ISSUE_ATTR_NAME = _issues
    NULL_REMOVAL = NULL_REMOVAL
    ARC_ENDPOINT_TOLERANCE_MODE = Auto
    REPAIR = Yes
    CONNECT_Z_MODE_SI = First Wins
    PRESETS = Custom
    TYPE_REPAIR = TYPE_REPAIR
    PASSED -> GeometryExtractor_2
    REPAIRED -> GeometryExtractor_2
GeometryExtractor_2
    OGCVERSION = 1.2
    KIND_LONG = OGC Well Known Binary
    REMOVE_GEOMETRY = Yes
    PREFER_POLYGON_OVER_SURFACE = Yes
    ATTR = _geometry_wkn
    -> GeometryReplacer_4
GeometryReplacer_4
    KIND_LONG = OGC Well Known Binary
    SOURCE = @Value(_geometry_wkn)
    ELLIPSOID_NAME = WGS84
    OUTPUT_POINT_DISPLAY = Point
    OGC_WKT_PRECISION_DISPLAY = 64-bit
    MSSQL_FORMAT_CHOICE = Geometry
    SRS_AXIS_ORDER_DISPLAY = Automatic
    REMOVE_ATTRIBUTE = Yes
    LETTERING = WGS84
    -> Orientor_2
Orientor_2
    KIND = RIGHT_HAND_RULE
    ORIENTED -> MultipleGeometryFilter_2
MultipleGeometryFilter_2
    CONTAINS -> GeometryPropertySetter_2
    NOT_CONTAINS -> GeometryPropertySetter_2
    INVALID -> Aggregator_4
Aggregator_4
    SEP = ,
    ORDERED = No
    GROUP_BY = gml_id
    AGGREGATE_TYPE = Homogeneous Collection (If Possible)
    MODE = Geometry - Assemble One Level
    ACCUM_ATTRS_NAME = Use Attributes From One Feature
    AGGREGATE -> GeometryPropertySetter_2
GeometryPropertySetter_2
    OVERWRITE_CHOICE = Yes
    SETTYPE_PARAM = Geometry Name
    GEOM_NAME_FIELD = geometry
    SET -> ZoningElement (writer INSPIRE_1) [off]
    SET -> CsmapReprojector_2

Bookmark: plu:SupplementaryRegulation
X2I_SupplementaryRegulation_extract
    GML_ID = @Value(gml_id)
    _XML_OUTPUT = @Value(_xml_output)
    X2I_SupplementaryRegulation_extract_Output -> FeatureMerger_5 [REQUESTOR]
AttributeSplitter_3
    ATTR_NAME = gml_id
    TRIM_OPTION = Both
    DELIMITER = _
    DROP_EMPTY_PARTS = No
    LIST_NAME = _list_regulation_key
    -> PythonCaller_createOfficialDocumentList_3
PythonCaller_createOfficialDocumentList_3
    PYTHONSOURCE:
      import fme
      import fmeobjects

      def createOfficialDocumentList(feature):
          listTexte = feature.getAttribute("_results_list_refTextInhalt{}")
          listBegruendung = feature.getAttribute("_results_list_refBegruendungInhalt{}")
          listDocuments = []

          if listTexte:
              for i in range(len(listTexte)):
                  listDocuments.append(listTexte[i])

          if listBegruendung:
              for j in range(len(listBegruendung)):
                  listDocuments.append(listBegruendung[j])

          if listDocuments:
              for k in range(len(listDocuments)):
                  attrName = "officialDocument{" + str(k) + "}" + ".xlink_href"
                  feature.setAttribute(attrName,listDocuments[k])
    NEW_ATTRIBUTES = officialDocument{}.xlink_href
    PYTHONSYMBOL = createOfficialDocumentList
    -> PythonCaller_createOfficialDocumentSqlStatement_3
    -> Tester_10
PythonCaller_createOfficialDocumentSqlStatement_3
    PYTHONSOURCE:
      import fme
      import fmeobjects

      def createOfficialDocumentSqlStatement(feature):
          listTexte = feature.getAttribute("_results_list_refTextInhalt{}")
          listBegruendung = feature.getAttribute("_results_list_refBegruendungInhalt{}")
          listDocuments = []

          sqlStrDocum = "SELECT gml_id, ft_type, binary_object FROM xplan41.gml_objects WHERE gml_id LIKE '"
          sqlStrOr = "' OR gml_id LIKE '"
          sqlStrEnd = "';"

          if listTexte:
              for i in range(len(listTexte)):
                  listDocuments.append(listTexte[i])

          if listBegruendung:
              for j in range(len(listBegruendung)):
                  listDocuments.append(listBegruendung[j])

          if listDocuments:
              for k in range(len(listDocuments)):
                  if k == 0:
                      docRef = listDocuments[k].replace("#", "")
                      sqlStrDocum += docRef
                  else:
                      sqlStrDocum += sqlStrOr
                      docRef = listDocuments[k].replace("#", "")
                      sqlStrDocum += docRef

              sqlStrDocum += sqlStrEnd
              feature.setAttribute("sqlStrStatementOfficialDocument",sqlStrDocum)
    NEW_ATTRIBUTES = sqlStrStatementOfficialDocument
    PYTHONSYMBOL = createOfficialDocumentSqlStatement
    -> Tester_20
Note: if zweckbestimmung has value
Tester_10
    BOOL_OP = OR
    TEST_MODE = Automatic
    TEST_CLAUSE = TEST @Value(_result_zweckbestimmung) ATTRIBUTE_HAS_VALUE ""
    TEST_DESCRIPTION = ""
    PASSED -> PythonCaller_findInCodeList_6
    FAILED -> Tester_11
PythonCaller_findInCodeList_6
    PYTHONSOURCE:
      import fme
      import fmeobjects

      def findInCodeList(feature):
          listHilucsKey = feature.getAttribute("_list_regulation_key{}")
          strCode = feature.getAttribute('_result_zweckbestimmung')
          strKey = ""
          findCode = False

          if listHilucsKey:
              strKey = listHilucsKey[1] + "_" + listHilucsKey[2] + "_zweckbestimmung_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_8
Tester_8
    BOOL_OP = OR
    TEST_MODE = Automatic
    TEST_CLAUSE = TEST @Value(_findInCodeList) = Yes
    TEST_DESCRIPTION = ""
    PASSED -> AttributeCreator_11
    FAILED -> Tester_11
AttributeCreator_11
    ATTR_TABLE = SET_TO _hilucs_key = @Value(_list_regulation_key{1})_@Value(_list_regulation_key{2})_zweckbestimmung_@Value(_result_zweckbestimmung)
    -> AttributeValueMapper_10
Note: if nutzungsform has value
Tester_11
    BOOL_OP = OR
    TEST_MODE = Automatic
    TEST_CLAUSE = TEST @Value(_result_nutzungsform) ATTRIBUTE_HAS_VALUE ""
    TEST_DESCRIPTION = ""
    PASSED -> PythonCaller_findInCodeList_7
    FAILED -> Tester_12
PythonCaller_findInCodeList_7
    PYTHONSOURCE:
      import fme
      import fmeobjects

      def findInCodeList(feature):
          listHilucsKey = feature.getAttribute("_list_regulation_key{}")
          strCode = feature.getAttribute('_result_nutzungsform')
          strKey = ""
          findCode = False

          if listHilucsKey:
              strKey = listHilucsKey[1] + "_" + listHilucsKey[2] + "_nutzungsform_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_9
Tester_9
    BOOL_OP = OR
    TEST_MODE = Automatic
    TEST_CLAUSE = TEST @Value(_findInCodeList) = Yes
    TEST_DESCRIPTION = ""
    PASSED -> AttributeCreator_12
    FAILED -> Tester_12
AttributeCreator_12
    ATTR_TABLE = SET_TO _hilucs_key = @Value(_list_regulation_key{1})_@Value(_list_regulation_key{2})_nutzungsform_@Value(_result_nutzungsform)
    -> AttributeValueMapper_10
Note: if ziel has value
Tester_12
    BOOL_OP = OR
    TEST_MODE = Automatic
    TEST_CLAUSE = TEST @Value(_result_ziel) ATTRIBUTE_HAS_VALUE ""
    TEST_DESCRIPTION = ""
    PASSED -> PythonCaller_findInCodeList_8
    FAILED -> Tester_13
PythonCaller_findInCodeList_8
    PYTHONSOURCE:
      import fme
      import fmeobjects

      def findInCodeList(feature):
          listHilucsKey = feature.getAttribute("_list_regulation_key{}")
          strCode = feature.getAttribute('_result_ziel')
          strKey = ""
          findCode = False

          if listHilucsKey:
              strKey = listHilucsKey[1] + "_" + listHilucsKey[2] + "_ziel_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_21
Tester_21
    BOOL_OP = OR
    TEST_MODE = Automatic
    TEST_CLAUSE = TEST @Value(_findInCodeList) = Yes
    TEST_DESCRIPTION = ""
    PASSED -> AttributeCreator_13
    FAILED -> Tester_13
AttributeCreator_13
    ATTR_TABLE = SET_TO _hilucs_key = @Value(_list_regulation_key{1})_@Value(_list_regulation_key{2})_ziel_@Value(_result_ziel)
    -> AttributeValueMapper_10
Note: if besondereArtDerBaulNutzung has value
Tester_13
    BOOL_OP = OR
    TEST_MODE = Automatic
    TEST_CLAUSE = TEST @Value(_result_besondereArtDerBaulNutzung) ATTRIBUTE_HAS_VALUE ""
    TEST_DESCRIPTION = ""
    PASSED -> PythonCaller_findInCodeList_9
    FAILED -> Tester_14
PythonCaller_findInCodeList_9
    PYTHONSOURCE:
      import fme
      import fmeobjects

      def findInCodeList(feature):
          listHilucsKey = feature.getAttribute("_list_regulation_key{}")
          strCode = feature.getAttribute('_result_besondereArtDerBaulNutzung')
          strKey = ""
          findCode = False

          if listHilucsKey:
              strKey = listHilucsKey[1] + "_" + listHilucsKey[2] + "_besondereArtDerBaulNutzung_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_23
Tester_23
    BOOL_OP = OR
    TEST_MODE = Automatic
    TEST_CLAUSE = TEST @Value(_findInCodeList) = Yes
    TEST_DESCRIPTION = ""
    PASSED -> AttributeCreator_14
    FAILED -> Tester_14
AttributeCreator_14
    ATTR_TABLE = SET_TO _hilucs_key = @Value(_list_regulation_key{1})_@Value(_list_regulation_key{2})_besondereArtDerBaulNutzung_@Value(_result_besondereArtDerBaulNutzung)
    -> AttributeValueMapper_10
Note: if allgArtDerBaulNutzung has value
Tester_14
    BOOL_OP = OR
    TEST_MODE = Automatic
    TEST_CLAUSE = TEST @Value(_result_allgArtDerBaulNutzung) ATTRIBUTE_HAS_VALUE ""
    TEST_DESCRIPTION = ""
    PASSED -> PythonCaller_findInCodeList_10
    FAILED -> Tester_15
PythonCaller_findInCodeList_10
    PYTHONSOURCE:
      import fme
      import fmeobjects

      def findInCodeList(feature):
          listHilucsKey = feature.getAttribute("_list_regulation_key{}")
          strCode = feature.getAttribute('_result_allgArtDerBaulNutzung')
          strKey = ""
          findCode = False

          if listHilucsKey:
              strKey = listHilucsKey[1] + "_" + listHilucsKey[2] + "_allgArtDerBaulNutzung_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_24
Tester_24
    BOOL_OP = OR
    TEST_MODE = Automatic
    TEST_CLAUSE = TEST @Value(_findInCodeList) = Yes
    TEST_DESCRIPTION = ""
    PASSED -> AttributeCreator_15
    FAILED -> Tester_15
AttributeCreator_15
    ATTR_TABLE = SET_TO _hilucs_key = @Value(_list_regulation_key{1})_@Value(_list_regulation_key{2})_allgArtDerBaulNutzung_@Value(_result_allgArtDerBaulNutzung)
    -> AttributeValueMapper_10
Note: if grund has value
Tester_15
    BOOL_OP = OR
    TEST_MODE = Automatic
    TEST_CLAUSE = TEST @Value(_result_grund) ATTRIBUTE_HAS_VALUE ""
    TEST_DESCRIPTION = ""
    PASSED -> PythonCaller_findInCodeList_11
    FAILED -> Tester_16
PythonCaller_findInCodeList_11
    PYTHONSOURCE:
      import fme
      import fmeobjects

      def findInCodeList(feature):
          listHilucsKey = feature.getAttribute("_list_regulation_key{}")
          strCode = feature.getAttribute('_result_grund')
          strKey = ""
          findCode = False

          if listHilucsKey:
              strKey = listHilucsKey[1] + "_" + listHilucsKey[2] + "_grund_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_22
Tester_22
    BOOL_OP = OR
    TEST_MODE = Automatic
    TEST_CLAUSE = TEST @Value(_findInCodeList) = Yes
    TEST_DESCRIPTION = ""
    PASSED -> AttributeCreator_16
    FAILED -> Tester_16
AttributeCreator_16
    ATTR_TABLE = SET_TO _hilucs_key = @Value(_list_regulation_key{1})_@Value(_list_regulation_key{2})_grund_@Value(_result_grund)
    -> AttributeValueMapper_10
Note: if massnahme has value
Tester_16
    BOOL_OP = OR
    TEST_MODE = Automatic
    TEST_CLAUSE = TEST @Value(_result_massnahme) ATTRIBUTE_HAS_VALUE ""
    TEST_DESCRIPTION = ""
    PASSED -> PythonCaller_findInCodeList_12
    FAILED -> Tester_17
PythonCaller_findInCodeList_12
    PYTHONSOURCE:
      import fme
      import fmeobjects

      def findInCodeList(feature):
          listHilucsKey = feature.getAttribute("_list_regulation_key{}")
          strCode = feature.getAttribute('_result_massnahme')
          strKey = ""
          findCode = False

          if listHilucsKey:
              strKey = listHilucsKey[1] + "_" + listHilucsKey[2] + "_massnahme_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_25
Tester_25
    BOOL_OP = OR
    TEST_MODE = Automatic
    TEST_CLAUSE = TEST @Value(_findInCodeList) = Yes
    TEST_DESCRIPTION = ""
    PASSED -> AttributeCreator_17
    FAILED -> Tester_17
AttributeCreator_17
    ATTR_TABLE = SET_TO _hilucs_key = @Value(_list_regulation_key{1})_@Value(_list_regulation_key{2})_massnahme_@Value(_result_massnahme)
    -> AttributeValueMapper_10
Note: if typ has value
Tester_17
    BOOL_OP = OR
    TEST_MODE = Automatic
    TEST_CLAUSE = TEST @Value(_result_typ) ATTRIBUTE_HAS_VALUE ""
    TEST_DESCRIPTION = ""
    PASSED -> PythonCaller_findInCodeList_13
    FAILED -> Tester_18
PythonCaller_findInCodeList_13
    PYTHONSOURCE:
      import fme
      import fmeobjects

      def findInCodeList(feature):
          listHilucsKey = feature.getAttribute("_list_regulation_key{}")
          strCode = feature.getAttribute('_result_typ')
          strKey = ""
          findCode = False

          if listHilucsKey:
              strKey = listHilucsKey[1] + "_" + listHilucsKey[2] + "_typ_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_26
Tester_26
    BOOL_OP = OR
    TEST_MODE = Automatic
    TEST_CLAUSE = TEST @Value(_findInCodeList) = Yes
    TEST_DESCRIPTION = ""
    PASSED -> AttributeCreator_18
    FAILED -> Tester_18
AttributeCreator_18
    ATTR_TABLE = SET_TO _hilucs_key = @Value(_list_regulation_key{1})_@Value(_list_regulation_key{2})_typ_@Value(_result_typ)
    -> AttributeValueMapper_10
Note: if verlaengerung has value
Tester_18
    BOOL_OP = OR
    TEST_MODE = Automatic
    TEST_CLAUSE = TEST @Value(_result_verlaengerung) ATTRIBUTE_HAS_VALUE ""
    TEST_DESCRIPTION = ""
    PASSED -> PythonCaller_findInCodeList_14
    FAILED -> Tester_19
PythonCaller_findInCodeList_14
    PYTHONSOURCE:
      import fme
      import fmeobjects

      def findInCodeList(feature):
          listHilucsKey = feature.getAttribute("_list_regulation_key{}")
          strCode = feature.getAttribute('_result_verlaengerung')
          strKey = ""
          findCode = False

          if listHilucsKey:
              strKey = listHilucsKey[1] + "_" + listHilucsKey[2] + "_verlaengerung_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_27
Tester_27
    BOOL_OP = OR
    TEST_MODE = Automatic
    TEST_CLAUSE = TEST @Value(_findInCodeList) = Yes
    TEST_DESCRIPTION = ""
    PASSED -> AttributeCreator_19
    FAILED -> Tester_19
AttributeCreator_19
    ATTR_TABLE = SET_TO _hilucs_key = @Value(_list_regulation_key{1})_@Value(_list_regulation_key{2})_verlaengerung_@Value(_result_verlaengerung)
    -> AttributeValueMapper_10
Note: if zulaessigkeit has value
Tester_19
    BOOL_OP = OR
    TEST_MODE = Automatic
    TEST_CLAUSE = TEST @Value(_result_zulaessigkeit) ATTRIBUTE_HAS_VALUE ""
    TEST_DESCRIPTION = ""
    PASSED -> PythonCaller_findInCodeList_15
    FAILED -> AttributeCreator_22
PythonCaller_findInCodeList_15
    PYTHONSOURCE:
      import fme
      import fmeobjects

      def findInCodeList(feature):
          listHilucsKey = feature.getAttribute("_list_regulation_key{}")
          strCode = feature.getAttribute('_result_zulaessigkeit')
          strKey = ""
          findCode = False

          if listHilucsKey:
              strKey = listHilucsKey[1] + "_" + listHilucsKey[2] + "_zulaessigkeit_" + strCode

              readerBp = open("codes/BP_Plan_Values_SupplementaryRegulation_formatiert.csv", "r")
              for line in readerBp:
                  spalten = line.split(";")
                  readerKey = spalten[0]

                  if strKey == readerKey:
                      findCode = True
                      break

              if findCode == False:
                  readerSo = open("codes/SO_Plan_Values_SupplementaryRegulation_formatiert.csv", "r")
                  for line in readerSo:
                      spalten = line.split(";")
                      readerKey = spalten[0]

                      if strKey == readerKey:
                          findCode = true
                          break

          feature.setAttribute("_findInCodeList",findCode)
    NEW_ATTRIBUTES = _findInCodeList
    PYTHONSYMBOL = findInCodeList
    -> Tester_28
Tester_28
    BOOL_OP = OR
    TEST_MODE = Automatic
    TEST_CLAUSE = TEST @Value(_findInCodeList) = Yes
    TEST_DESCRIPTION = ""
    PASSED -> AttributeCreator_20
    FAILED -> AttributeCreator_22
AttributeCreator_20
    ATTR_TABLE = SET_TO _hilucs_key = @Value(_list_regulation_key{1})_@Value(_list_regulation_key{2})_zulaessigkeit_@Value(_result_zulaessigkeit)
    -> AttributeValueMapper_10
AttributeCreator_22
    ATTR_TABLE = SET_TO _hilucs_key = @Value(_list_regulation_key{1})_@Value(_list_regulation_key{2})__
    -> AttributeValueMapper_10
AttributeValueMapper_10
    SRC = _hilucs_key
    VAL_ATTR = _supplementaryRegulation_value
    LUT =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
    DIRECTION = Forward (Source To Destination)
    -> AttributeValueMapper_11
AttributeValueMapper_11
    SRC = _hilucs_key
    VAL_ATTR = _specificSupplementaryRegulation_value
    LUT =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
    DIRECTION = Forward (Source To Destination)
    -> AttributeValueMapper_8
AttributeValueMapper_8
    SRC = _result_rechtsstand
    VAL_ATTR = _SpatialPlan.processStepGeneral
    LUT = 1000,elaboration,2000,elaboration,2100,elaboration,2200,elaboration,2300,elaboration,2400,elaboration,3000,adoption,4000,legalForce,4500,obsolete,5000,obsolete
    DIRECTION = Forward (Source To Destination)
    -> AttributeValueMapper_9
AttributeValueMapper_9
    SRC = _result_rechtscharakter
    VAL_ATTR = _regulationNature
    LUT = 1000,generallyBinding,2000,generallyBinding,3000,nonBinding,4000,definedInLegislation,5000,definedInLegislation,9998,nonBinding
    DIRECTION = Forward (Source To Destination)
    -> Tester_2
Tester_2
    BOOL_OP = OR
    TEST_MODE = Automatic
    TEST_CLAUSE:
      TEST @Value(_supplementaryRegulation_value) NOT_ATTRIBUTE_HAS_VALUE ""
      TEST _supplementaryRegulation_value ATTRIBUTE_IS_MISSING ""
      TEST _supplementaryRegulation_value ATTRIBUTE_VALUE_NULL ""
      TEST _supplementaryRegulation_value ATTRIBUTE_IS_EMPTY ""
    TEST_DESCRIPTION = ""
    PASSED -> AttributeCreator_28
    FAILED -> AttributeSplitter_4
AttributeCreator_28
    ATTR_TABLE:
      SET_TO _supplementaryRegulation_value = error
      SET_TO _specificSupplementaryRegulation_value = error
    -> AttributeSplitter_4
AttributeSplitter_4
    ATTR_NAME = _supplementaryRegulation_value
    TRIM_OPTION = Both
    DELIMITER = &&
    DROP_EMPTY_PARTS = No
    LIST_NAME = _supplementaryRegulation_values_list
    -> PythonCaller_12
PythonCaller_12
    PYTHONSOURCE:
      import fme
      import fmeobjects

      def setSupplementaryRegulationValues(feature):
          listSupplementaryRegulationValues = feature.getAttribute("_supplementaryRegulation_values_list{}")

          if listSupplementaryRegulationValues:
              for i in range(len(listSupplementaryRegulationValues)):
                  if listSupplementaryRegulationValues[i]:
                      attrName = "supplementaryRegulation{" + str(i) + "}" + ".xlink_href"
                      strRegulation = "http://inspire.ec.europa.eu/codelist/SupplementaryRegulationValue/" + listSupplementaryRegulationValues[i]
                      feature.setAttribute(attrName,strRegulation)
    PYTHONSYMBOL = setSupplementaryRegulationValues
    -> PythonCaller_dimensions
PythonCaller_dimensions
    PYTHONSOURCE:
      # -*- coding: UTF-8 -*-
      import fme
      import fmeobjects
      import xml.etree.ElementTree as ET

      def setDimensionsValues(feature):
          strXml = feature.getAttribute("_result_hoehenangabe")
          strXmlEncode = strXml.encode(encoding='UTF-8')
          root = ET.fromstring(strXmlEncode)

          hoehenbezug = {"absolutNHM": 1000, "relativGelaendeoberkante": 2000, "relativGehwegOberkante": 2500, "relativBezugshoehe": 3000}
          bezugspunkt = {"TH": 1000, "FH": 2000, "OK": 3000, "LH": 3500, "SH": 4000, "EFH": 4500, "HBA": 5000, "UK": 5500, "GBH": 6000}
          countElements = -1

          for element in root.iter('out'):
              countElements += 1
              indicationReference = ""
              value = ""

              hoehenbereich = False
              tmpIndicationReference = ""
              indicationReference2 = ""
              value2 = ""

              if len(list(element)) > 0:
                  for i in range(len(list(element))):
                      if element[i].tag == '{http://www.xplanung.de/xplangml/4/1}hoehenbezug':
                          for dictKey, dictValue in hoehenbezug.items():
                              if element[i].text == str(dictValue):
                                  indicationReference += dictKey
                                  break
                      elif element[i].tag == '{http://www.xplanung.de/xplangml/4/1}abweichenderHoehenbezug':
                          indicationReference += element[i].text
                      elif element[i].tag == '{http://www.xplanung.de/xplangml/4/1}bezugspunkt':
                          for dictKey, dictValue in bezugspunkt.items():
                              if element[i].text == str(dictValue):
                                  indicationReference += "_" + dictKey
                                  break
                      elif element[i].tag == '{http://www.xplanung.de/xplangml/4/1}abweichenderBezugspunkt':
                          indicationReference += "_" + element[i].text
                      elif element[i].tag == '{http://www.xplanung.de/xplangml/4/1}h' or element[i].tag == '{http://www.xplanung.de/xplangml/4/1}hZwingend':
                          indicationReference += "_" + element[i].tag.replace("{http://www.xplanung.de/xplangml/4/1}", "")
                          value = float(element[i].text)
                      elif element[i].tag == '{http://www.xplanung.de/xplangml/4/1}hMin' or element[i].tag == '{http://www.xplanung.de/xplangml/4/1}hMax':
                          if hoehenbereich == False:
                              tmpIndicationReference = indicationReference
                              indicationReference += "_" + element[i].tag.replace("{http://www.xplanung.de/xplangml/4/1}", "")
                              value = float(element[i].text)
                              hoehenbereich = True
                          else:
                              indicationReference2 += tmpIndicationReference
                              indicationReference2 += "_" + element[i].tag.replace("{http://www.xplanung.de/xplangml/4/1}", "")
                              value2 = float(element[i].text)

              attrNameRef = "dimensioningIndication{" + str(countElements) + "}" + ".DimensioningIndicationMeasureValue.indicationReference"
              attrNameVal = "dimensioningIndication{" + str(countElements) + "}" + ".DimensioningIndicationMeasureValue.value"
              attrNameUom = "dimensioningIndication{" + str(countElements) + "}" + ".DimensioningIndicationMeasureValue.value.uom"
              feature.setAttribute(attrNameRef,indicationReference)
              feature.setAttribute(attrNameVal,str(value))
              feature.setAttribute(attrNameUom,"m")

              if hoehenbereich == True and indicationReference2 != "" and value2 != "":
                  countElements += 1
                  attrNameRef = "dimensioningIndication{" + str(countElements) + "}" + ".DimensioningIndicationMeasureValue.indicationReference"
                  attrNameVal = "dimensioningIndication{" + str(countElements) + "}" + ".DimensioningIndicationMeasureValue.value"
                  attrNameUom = "dimensioningIndication{" + str(countElements) + "}" + ".DimensioningIndicationMeasureValue.value.uom"
                  feature.setAttribute(attrNameRef,indicationReference2)
                  feature.setAttribute(attrNameVal,str(value2))
                  feature.setAttribute(attrNameUom,"m")

          feature.setAttribute("dimensCount1",countElements)
    NEW_ATTRIBUTES = dimensCount1
    PYTHONSYMBOL = setDimensionsValues
    -> PythonCaller_dimensions_3
PythonCaller_dimensions_3
    PYTHONSOURCE:
      # -*- coding: UTF-8 -*-
      import fme
      import fmeobjects
      import xml.etree.ElementTree as ET

      def setDimensionsValues(feature):
          strXml = feature.getAttribute('_result_spezielleAttribute')
          strXmlEncode = strXml.encode(encoding='UTF-8')
          root = ET.fromstring(strXmlEncode)

          dictType = {"MaxAnzahlWohnungen": "Integer","Zmin": "Integer","Zmax": "Integer","Zzwingend": "Integer","Z": "Integer","Z_Ausn": "Integer","Z_Staffel": "Integer","Z_Dach": "Integer","ZUmin": "Integer","ZUmax": "Integer","ZUzwingend": "Integer","ZU": "Integer","ZU_Ausn": "Integer","GFZmin": "Real","GFZmax": "Real","GFZ": "Real","GFZ_Ausn": "Real","BMZ": "Real","BMZ_Ausn": "Real","GRZ": "Real","GRZmin": "Real","GRZmax": "Real","GRZ_Ausn": "Real","Fmin": "Measure","Fmax": "Measure","Bmin": "Measure","Bmax": "Measure","Tmin": "Measure","Tmax": "Measure","GFmin": "Measure","GFmax": "Measure","GF": "Measure","GF_Ausn": "Measure","BM": "Measure","BM_Ausn": "Measure","GRmin": "Measure","GRmax": "Measure","GR": "Measure","GR_Ausn": "Measure","DNmin": "Measure","DNmax": "Measure","DN": "Measure","DNZwingend": "Measure","FR": "Measure","dachform": "dictDachform","ZWohn": "Integer","GFAntWohnen": "Measure","GFWohnen": "Measure","GFAntGewerbe": "Measure","GFGewerbe": "Measure","wohnnutzungEGStrasse": "dictWohnnutzungEGStrasse","bauweise": "dictBauweise","bebauungsArt": "dictBebauungsArt"}
          dictDachform = {"Flachdach": 1000, "Pultdach": 2100, "VersetztesPultdach": 2200, "Satteldach": 3100, "Walmdach": 3200, "Krueppelwalmdach": 3300, "Mansardendach": 3400, "Zeltdach": 3500, "Kegeldach": 3600, "Kuppeldach": 3700, "Sheddach": 3800, "Bogendach": 3900, "Turmdach": 4000, "Mischform": 5000, "Sonstiges": 9999}
          dictWohnnutzungEGStrasse = {"Zulaessig": 1000, "NichtZulaessig": 2000, "Ausnahmsweise": 3000}
          dictBauweise = {"OffeneBauweise": 1000, "Geschlossene": 2000, "Abweichende": 3000}
          dictBebauungsArt = {"Einzelhaeuser": 1000, "Doppelhaeuser": 2000, "Hausgruppen": 3000, "EinzelDoppelhaeuser": 4000, "Einzelhaeuser": 5000, "Doppelhaeuser": 6000, "Reihenhaeuser": 7000}
          dictMeasure = {"Fmin": "m2","Fmax": "m2","Bmin": "m","Bmax": "m","Tmin": "m","Tmax": "m","GFmin": "m2","GFmax": "m2","GF": "m2","GF_Ausn": "m2","BM": "m3","BM_Ausn": "m3","GRmin": "m2","GRmax": "m2","GR": "m2","GR_Ausn": "m2","DNmin": "deg","DNmax": "deg","DN": "deg","DNZwingend": "deg","FR": "deg","GFAntWohnen": "scale","GFWohnen": "m2","GFAntGewerbe": "scale","GFGewerbe": "m2"}

          countElements = feature.getAttribute('dimensCount1')

          for element in root.iter('out'):
              if len(list(element)) > 0:
                  for i in range(len(list(element))):
                      indicationReference = ""
                      value = ""
                      uom = ""
                      typ = ""

                      countElements += 1
                      tag = element[i].tag.replace("{http://www.xplanung.de/xplangml/4/1}", "")

                      for dictKeyType, dictValueType in dictType.items():
                          if tag == dictKeyType:
                              if dictValueType == "Integer":
                                  indicationReference = tag
                                  value = int(element[i].text)
                                  typ = "Integer"
                                  break
                              elif dictValueType == "Real":
                                  indicationReference = tag
                                  value = float(element[i].text)
                                  typ = "Real"
                                  break
                              elif dictValueType == "Measure":
                                  for dictKeyMeasure, dictValueMeasure in dictMeasure.items():
                                      if tag == dictKeyMeasure:
                                          indicationReference = tag
                                          value = float(element[i].text)
                                          typ = "Measure"
                                          uom = dictValueMeasure
                                          break
                              elif dictValueType == "dictDachform":
                                  for dictKeyDachform, dictValueDachform in dictDachform.items():
                                      if int(element[i].text) == int(dictValueDachform):
                                          indicationReference = "Dachform"
                                          value = dictKeyDachform
                                          typ = "Character"
                                          break
                              elif dictValueType == "dictWohnnutzungEGStrasse":
                                  for dictKeyWohnnutzungEGStrasse, dictValueWohnnutzungEGStrasse in dictWohnnutzungEGStrasse.items():
                                      if int(element[i].text) == int(dictValueWohnnutzungEGStrasse):
                                          indicationReference = "wohnnutzungEGStrasse"
                                          value = dictKeyWohnnutzungEGStrasse
                                          typ = "Character"
                                          break
                              elif dictValueType == "dictBauweise":
                                  for dictKeyBauweise, dictValueBauweise in dictBauweise.items():
                                      if int(element[i].text) == int(dictValueBauweise):
                                          indicationReference = "Bauweise"
                                          value = dictKeyBauweise
                                          typ = "Character"
                                          break
                              elif dictValueType == "dictBebauungsArt":
                                  for dictKeyBebauungsArt, dictValueBebauungsArt in dictBebauungsArt.items():
                                      if int(element[i].text) == int(dictValueBebauungsArt):
                                          indicationReference = "BebauungsArt"
                                          value = dictKeyBebauungsArt
                                          typ = "Character"
                                          break

                      if typ == "Integer":
                          attrNameRef = "dimensioningIndication{" + str(countElements) + "}" + ".DimensioningIndicationIntegerValue.indicationReference"
                          attrNameVal = "dimensioningIndication{" + str(countElements) + "}" + ".DimensioningIndicationIntegerValue.value"
                          feature.setAttribute(attrNameRef,indicationReference)
                          feature.setAttribute(attrNameVal,str(value))
                      elif typ == "Real":
                          attrNameRef = "dimensioningIndication{" + str(countElements) + "}" + ".DimensioningIndicationRealValue.indicationReference"
                          attrNameVal = "dimensioningIndication{" + str(countElements) + "}" + ".DimensioningIndicationRealValue.value"
                          feature.setAttribute(attrNameRef,indicationReference)
                          feature.setAttribute(attrNameVal,str(value))
                      elif typ == "Measure":
                          attrNameRef = "dimensioningIndication{" + str(countElements) + "}" + ".DimensioningIndicationMeasureValue.indicationReference"
                          attrNameVal = "dimensioningIndication{" + str(countElements) + "}" + ".DimensioningIndicationMeasureValue.value"
                          attrNameUom = "dimensioningIndication{" + str(countElements) + "}" + ".DimensioningIndicationMeasureValue.value.uom"
                          feature.setAttribute(attrNameRef,indicationReference)
                          feature.setAttribute(attrNameVal,str(value))
                          feature.setAttribute(attrNameUom,uom)
                      elif typ == "Character":
                          attrNameRef = "dimensioningIndication{" + str(countElements) + "}" + ".DimensioningIndicationCharacterValue.indicationReference"
                          attrNameVal = "dimensioningIndication{" + str(countElements) + "}" + ".DimensioningIndicationCharacterValue.value"
                          feature.setAttribute(attrNameRef,indicationReference)
                          feature.setAttribute(attrNameVal,value)
    PYTHONSYMBOL = setDimensionsValues
    -> AttributeCreator_10
Note: optionales Zielattribut für das optionale xplan-Attribute "hatGenerAttribut" wegelassen!
AttributeCreator_10
    ATTR_TABLE:
      SET_TO gml_id = @Value(gml_id)
      SET_TO gml_identifier.codeSpace = http://inspire.ec.europa.eu/ids
      SET_TO gml_identifier = https://registry.gdi-de.org/id/de.hh/0a2b2809-dd93-45e6-bc0e-26093eb1122a/@Value(gml_id)
      SET_TO inspireId.Identifier.localId = @Value(gml_id)
      SET_TO inspireId.Identifier.namespace = https://registry.gdi-de.org/id/de.hh/0a2b2809-dd93-45e6-bc0e-26093eb1122a
      SET_TO beginLifespanVersion.nilReason = other:unpopulated
      SET_TO beginLifespanVersion.xsi_nil = true
      SET_TO endLifespanVersion.nilReason = other:unpopulated
      SET_TO endLifespanVersion.xsi_nil = true
      SET_TO specificSupplementaryRegulation{0}.xlink_href = FME_CONDITIONAL:DEFAULT_VALUE'_FME_NO_OP_'BOOL_OP;OR;COMPOSITE_TEST;<Unused>;TEST _specificSupplementaryRegulation_value NOT_ATTRIBUTE_IS_MISSING _FME_BLANK_STRING_'http://daten-hamburg.de/inspire/codelist/SpecificSupplementaryRegulationValue_Extension.xml#@Value(_specificSupplementaryRegulation_value)'FME_NUM_CONDITIONS2___
      SET_TO specificSupplementaryRegulation{0}.nilReason = FME_CONDITIONAL:DEFAULT_VALUE'_FME_NO_OP_'BOOL_OP;OR;COMPOSITE_TEST;<Unused>;TEST _specificSupplementaryRegulation_value ATTRIBUTE_IS_MISSING _FME_BLANK_STRING_'other:unpopulated'FME_NUM_CONDITIONS2___
      SET_TO specificSupplementaryRegulation{0}.xsi_nil = FME_CONDITIONAL:DEFAULT_VALUE'_FME_NO_OP_'BOOL_OP;OR;COMPOSITE_TEST;<Unused>;TEST _specificSupplementaryRegulation_value ATTRIBUTE_IS_MISSING _FME_BLANK_STRING_'true'FME_NUM_CONDITIONS2___
      SET_TO processStepGeneral.xlink_href = FME_CONDITIONAL:DEFAULT_VALUE'_FME_NO_OP_'BOOL_OP;OR;COMPOSITE_TEST;<Unused>;TEST _result_rechtsstand NOT_ATTRIBUTE_IS_MISSING _FME_BLANK_STRING_'http://inspire.ec.europa.eu/codelist/ProcessStepGeneralValue/@Value(_SpatialPlan.processStepGeneral)'FME_NUM_CONDITIONS2___
      SET_TO processStepGeneral.nilReason = FME_CONDITIONAL:DEFAULT_VALUE'_FME_NO_OP_'BOOL_OP;OR;COMPOSITE_TEST;<Unused>;TEST _result_rechtsstand ATTRIBUTE_IS_MISSING _FME_BLANK_STRING_'other:unpopulated'FME_NUM_CONDITIONS2___
      SET_TO processStepGeneral.xsi_nil = FME_CONDITIONAL:DEFAULT_VALUE'_FME_NO_OP_'BOOL_OP;OR;COMPOSITE_TEST;<Unused>;TEST _result_rechtsstand ATTRIBUTE_IS_MISSING _FME_BLANK_STRING_'true'FME_NUM_CONDITIONS2___
      SET_TO inheritedFromOtherPlans.nilReason = other:unpopulated
      SET_TO inheritedFromOtherPlans.xsi_nil = true
      SET_TO specificRegulationNature.nilReason = other:unpopulated
      SET_TO specificRegulationNature.xsi_nil = true
      SET_TO regulationNature.xlink_href = FME_CONDITIONAL:DEFAULT_VALUE'http://inspire.ec.europa.eu/codelist/RegulationNatureValue/default'BOOL_OP;OR;COMPOSITE_TEST;<Unused>;TEST _result_rechtscharakter NOT_ATTRIBUTE_IS_MISSING _FME_BLANK_STRING_'http://inspire.ec.europa.eu/codelist/RegulationNatureValue/@Value(_regulationNature)'FME_NUM_CONDITIONS2___
      SET_TO _regulationNature.nilReason = FME_CONDITIONAL:DEFAULT_VALUE'_FME_NO_OP_'BOOL_OP;OR;COMPOSITE_TEST;<Unused>;TEST _result_rechtscharakter ATTRIBUTE_IS_MISSING _FME_BLANK_STRING_'other:unpopulated'FME_NUM_CONDITIONS2___
      SET_TO _regulationNature.xsi_nil = FME_CONDITIONAL:DEFAULT_VALUE'_FME_NO_OP_'BOOL_OP;OR;COMPOSITE_TEST;<Unused>;TEST _result_rechtscharakter ATTRIBUTE_IS_MISSING _FME_BLANK_STRING_'true'FME_NUM_CONDITIONS2___
      SET_TO _supplementaryRegulation{0}.xlink_href = _Info: http://inspire.ec.europa.eu/codelist/SupplementaryRegulationValue
      SET_TO _supplementaryRegulation{0}.nilReason = FME_CONDITIONAL:DEFAULT_VALUE'_FME_NO_OP_'BOOL_OP;OR;COMPOSITE_TEST;<Unused>;TEST _supplementaryRegulation_value ATTRIBUTE_IS_MISSING _FME_BLANK_STRING_'other:unpopulated'FME_NUM_CONDITIONS2___
      SET_TO _supplementaryRegulation{0}.xsi_nil = FME_CONDITIONAL:DEFAULT_VALUE'_FME_NO_OP_'BOOL_OP;OR;COMPOSITE_TEST;<Unused>;TEST _supplementaryRegulation_value ATTRIBUTE_IS_MISSING _FME_BLANK_STRING_'true'FME_NUM_CONDITIONS2___
      SET_TO backgroundMap.nilReason = other:unpopulated
      SET_TO backgroundMap.xsi_nil = true
      SET_TO _officialDocument{0}.xlink_href = _Info: py
      SET_TO plan.xlink_href = #@Value(gml_id_plan)
      SET_TO validFrom = FME_CONDITIONAL:DEFAULT_VALUE'_FME_NO_OP_'BOOL_OP;OR;COMPOSITE_TEST;<Unused>;TEST _result_startBedingung NOT_ATTRIBUTE_IS_MISSING _FME_BLANK_STRING_'@Value(_result_startBedingung)'FME_NUM_CONDITIONS2___
      SET_TO validTo = FME_CONDITIONAL:DEFAULT_VALUE'_FME_NO_OP_'BOOL_OP;OR;COMPOSITE_TEST;<Unused>;TEST _result_endeBedingung NOT_ATTRIBUTE_IS_MISSING _FME_BLANK_STRING_'@Value(_result_endeBedingung)'FME_NUM_CONDITIONS2___
    -> GeometryReplacer_7

Bookmark: plu:OfficialDocumentation
Tester_20
    BOOL_OP = OR
    TEST_MODE = Automatic
    TEST_CLAUSE = TEST sqlStrStatementOfficialDocument NOT_ATTRIBUTE_IS_MISSING ""
    TEST_DESCRIPTION = ""
    PASSED -> X2I_OfficialDocumentation_extract [X2I_OfficialDocumentation_extract_Input]
X2I_OfficialDocumentation_extract
    SQLSTRSTATEMENTOFFICIALDOCUMENT = @Value(sqlStrStatementOfficialDocument)
    GML_ID = @Value(gml_id)
    X2I_OfficialDocumentation_extract_Output -> AttributeValueMapper_12 [off]
    X2I_OfficialDocumentation_extract_Output -> PythonCaller_setPlanDocumentLinkList
Note: für XP_SpezExterneReferenz.typ (Tabelle 16) ab 5.0! / Attribute _result_spezExRef_typ
AttributeValueMapper_12 [off]
    VAL_ATTR = _looked_up
    DIRECTION = Forward (Source To Destination)
    -> PythonCaller_setPlanDocumentLinkList [off]
PythonCaller_setPlanDocumentLinkList
    PYTHONSOURCE:
      import fme
      import fmeobjects

      def setPlanDocumentLinkList(feature):
          linkGeorefURL = feature.getAttribute('_result_refScan_georefURL')
          linkReferenzURL = feature.getAttribute('_result_refScan_referenzURL')
          linkInformationssystemURL = feature.getAttribute('_result_refScan_informationssystemURL')
          listLinks = []

          if linkGeorefURL:
              listLinks.append(linkGeorefURL)

          if linkReferenzURL:
              listLinks.append(linkReferenzURL)

          if linkInformationssystemURL:
              listLinks.append(linkInformationssystemURL)

          if listLinks:
              for i in range(len(listLinks)):
                  attrName = "planDocument.DocumentCitation.link{" + str(i) + "}"
                  feature.setAttribute(attrName,listLinks[i])
    PYTHONSYMBOL = setPlanDocumentLinkList
    -> PythonCaller_setLegislationCitationLinkList
PythonCaller_setLegislationCitationLinkList
    PYTHONSOURCE:
      import fme
      import fmeobjects

      def setLegislationCitationLinkList(feature):
          linkGeorefURL = feature.getAttribute('_result_refText_georefURL')
          linkReferenzURL = feature.getAttribute('_result_refText_referenzURL')
          linkInformationssystemURL = feature.getAttribute('_result_refText_informationssystemURL')
          listLinks = []

          if linkGeorefURL:
              listLinks.append(linkGeorefURL)

          if linkReferenzURL:
              listLinks.append(linkReferenzURL)

          if linkInformationssystemURL:
              listLinks.append(linkInformationssystemURL)

          if listLinks:
              for i in range(len(listLinks)):
                  attrName = "legislationCitation.LegislationCitation.link{" + str(i) + "}"
                  feature.setAttribute(attrName,listLinks[i])
    PYTHONSYMBOL = setLegislationCitationLinkList
    -> AttributeCreator_21
AttributeCreator_21
    ATTR_TABLE:
      SET_TO gml_id = @Value(gml_id)
      SET_TO gml_identifier.codeSpace = http://inspire.ec.europa.eu/ids
      SET_TO gml_identifier = https://registry.gdi-de.org/id/de.hh/0a2b2809-dd93-45e6-bc0e-26093eb1122a/@Value(gml_id)
      SET_TO inspireId.Identifier.localId = @Value(gml_id)
      SET_TO inspireId.Identifier.namespace = https://registry.gdi-de.org/id/de.hh/0a2b2809-dd93-45e6-bc0e-26093eb1122a
      SET_TO regulationText = FME_CONDITIONAL:DEFAULT_VALUE'_FME_NO_OP_'BOOL_OP;OR;COMPOSITE_TEST;<Unused>;TEST _result_text NOT_ATTRIBUTE_IS_MISSING _FME_BLANK_STRING_'@ReplaceString(@Value(_result_text),"
        "," ")'FME_NUM_CONDITIONS2___
      SET_TO _regulationText.nilReason = FME_CONDITIONAL:DEFAULT_VALUE'_FME_NO_OP_'BOOL_OP;OR;COMPOSITE_TEST;<Unused>;TEST _result_text ATTRIBUTE_IS_MISSING _FME_BLANK_STRING_'other:unpopulated'FME_NUM_CONDITIONS2___
      SET_TO _regulationText.xsi_nil = FME_CONDITIONAL:DEFAULT_VALUE'_FME_NO_OP_'BOOL_OP;OR;COMPOSITE_TEST;<Unused>;TEST _result_text ATTRIBUTE_IS_MISSING _FME_BLANK_STRING_'true'FME_NUM_CONDITIONS2___
      SET_TO legislationCitation.LegislationCitation.gml_id = FME_CONDITIONAL:DEFAULT_VALUE'_FME_NO_OP_'BOOL_OP;OR;COMPOSITE_TEST;<Unused>;TEST @FindString(@Value(gml_id),"XPLAN_XP_BEGRUENDUNGABSCHNITT") != -1;TEST @FindString(@Value(gml_id),"XPLAN_XP_TEXTABSCHNITT") != -1'@Value(gml_id)_LS-0'FME_NUM_CONDITIONS2___
      SET_TO legislationCitation.LegislationCitation.name = FME_CONDITIONAL:DEFAULT_VALUE'_FME_NO_OP_'BOOL_OP;AND;COMPOSITE_TEST;<Unused>;TEST @FindString(@Value(gml_id),"XPLAN_XP_BEGRUENDUNGABSCHNITT") != -1;TEST _result_refText_referenzName NOT_ATTRIBUTE_IS_MISSING _FME_BLANK_STRING_'@Value(_result_refText_referenzName)'BOOL_OP;AND;COMPOSITE_TEST;<Unused>;TEST @FindString(@Value(gml_id),"XPLAN_XP_BEGRUENDUNGABSCHNITT") != -1;TEST _result_refText_referenzName ATTRIBUTE_IS_MISSING _FME_BLANK_STRING_'default'BOOL_OP;AND;COMPOSITE_TEST;<Unused>;TEST @FindString(@Value(gml_id),"XPLAN_XP_TEXTABSCHNITT") != -1;TEST _result_refText_referenzName NOT_ATTRIBUTE_IS_MISSING _FME_BLANK_STRING_'@Value(_result_refText_referenzName)'BOOL_OP;AND;COMPOSITE_TEST;<Unused>;TEST @FindString(@Value(gml_id),"XPLAN_XP_TEXTABSCHNITT") != -1;TEST _result_refText_referenzName ATTRIBUTE_IS_MISSING _FME_BLANK_STRING_'default'FME_NUM_CONDITIONS5___
      SET_TO legislationCitation.LegislationCitation.shortName = FME_CONDITIONAL:DEFAULT_VALUE'_FME_NO_OP_'BOOL_OP;OR;COMPOSITE_TEST;<Unused>;TEST @FindString(@Value(gml_id),"XPLAN_XP_BEGRUENDUNGABSCHNITT") != -1'BegruendungAbschnitt'BOOL_OP;OR;COMPOSITE_TEST;<Unused>;TEST @FindString(@Value(gml_id),"XPLAN_XP_TEXTABSCHNITT") != -1'TextAbschnitt'FME_NUM_CONDITIONS3___
      SET_TO legislationCitation.LegislationCitation.date.CI_Date.date.Date = FME_CONDITIONAL:DEFAULT_VALUE'_FME_NO_OP_'BOOL_OP;AND;COMPOSITE_TEST;<Unused>;TEST @FindString(@Value(gml_id),"XPLAN_XP_BEGRUENDUNGABSCHNITT") != -1;TEST _result_refText_datum NOT_ATTRIBUTE_IS_MISSING _FME_BLANK_STRING_'@Value(_result_refText_datum)'BOOL_OP;AND;COMPOSITE_TEST;<Unused>;TEST @FindString(@Value(gml_id),"XPLAN_XP_TEXTABSCHNITT") != -1;TEST _result_refText_datum NOT_ATTRIBUTE_IS_MISSING _FME_BLANK_STRING_'@Value(_result_refText_datum)'FME_NUM_CONDITIONS3___
      SET_TO legislationCitation.LegislationCitation.date.CI_Date.dateType.CI_DateTypeCode = FME_CONDITIONAL:DEFAULT_VALUE'_FME_NO_OP_'BOOL_OP;AND;COMPOSITE_TEST;<Unused>;TEST @FindString(@Value(gml_id),"XPLAN_XP_BEGRUENDUNGABSCHNITT") != -1;TEST _result_refText_datum NOT_ATTRIBUTE_IS_MISSING _FME_BLANK_STRING_'creation'BOOL_OP;AND;COMPOSITE_TEST;<Unused>;TEST @FindString(@Value(gml_id),"XPLAN_XP_TEXTABSCHNITT") != -1;TEST _result_refText_datum NOT_ATTRIBUTE_IS_MISSING _FME_BLANK_STRING_'creation'FME_NUM_CONDITIONS3___
      SET_TO legislationCitation.LegislationCitation.date.CI_Date.dateType.CI_DateTypeCode.codeList = FME_CONDITIONAL:DEFAULT_VALUE'_FME_NO_OP_'BOOL_OP;AND;COMPOSITE_TEST;<Unused>;TEST @FindString(@Value(gml_id),"XPLAN_XP_BEGRUENDUNGABSCHNITT") != -1;TEST _result_refText_datum NOT_ATTRIBUTE_IS_MISSING _FME_BLANK_STRING_'http://www.isotc211.org/2005/resources/Codelist/gmxCodelists.xml#CI_DateTypeCode'BOOL_OP;AND;COMPOSITE_TEST;<Unused>;TEST @FindString(@Value(gml_id),"XPLAN_XP_TEXTABSCHNITT") != -1;TEST _result_refText_datum NOT_ATTRIBUTE_IS_MISSING _FME_BLANK_STRING_'http://www.isotc211.org/2005/resources/Codelist/gmxCodelists.xml#CI_DateTypeCode'FME_NUM_CONDITIONS3___
      SET_TO legislationCitation.LegislationCitation.date.CI_Date.dateType.CI_DateTypeCode.codeListValue = FME_CONDITIONAL:DEFAULT_VALUE'_FME_NO_OP_'BOOL_OP;AND;COMPOSITE_TEST;<Unused>;TEST @FindString(@Value(gml_id),"XPLAN_XP_BEGRUENDUNGABSCHNITT") != -1;TEST _result_refText_datum NOT_ATTRIBUTE_IS_MISSING _FME_BLANK_STRING_'creation'BOOL_OP;AND;COMPOSITE_TEST;<Unused>;TEST @FindString(@Value(gml_id),"XPLAN_XP_TEXTABSCHNITT") != -1;TEST _result_refText_datum NOT_ATTRIBUTE_IS_MISSING _FME_BLANK_STRING_'creation'FME_NUM_CONDITIONS3___
      SET_TO _legislationCitation.LegislationCitation.link{0}
      SET_TO _legislationCitation.LegislationCitation.link{0}.nilReason
      SET_TO _legislationCitation.LegislationCitation.link{0}.xsi_nil
      SET_TO legislationCitation.LegislationCitation.level.xlink_href = FME_CONDITIONAL:DEFAULT_VALUE'_FME_NO_OP_'BOOL_OP;OR;COMPOSITE_TEST;<Unused>;TEST @FindString(@Value(gml_id),"XPLAN_XP_BEGRUENDUNGABSCHNITT") != -1;TEST @FindString(@Value(gml_id),"XPLAN_XP_TEXTABSCHNITT") != -1'http://inspire.ec.europa.eu/codelist/LegislationLevelValue/national'FME_NUM_CONDITIONS2___
      SET_TO planDocument.DocumentCitation.gml_id = FME_CONDITIONAL:DEFAULT_VALUE'_FME_NO_OP_'BOOL_OP;OR;COMPOSITE_TEST;<Unused>;TEST @FindString(@Value(gml_id),"XPLAN_XP_RASTERPLANBASIS") != -1'@Value(gml_id)_DC-0'FME_NUM_CONDITIONS2___
      SET_TO planDocument.DocumentCitation.name = FME_CONDITIONAL:DEFAULT_VALUE'_FME_NO_OP_'BOOL_OP;AND;COMPOSITE_TEST;<Unused>;TEST @FindString(@Value(gml_id),"XPLAN_XP_RASTERPLANBASIS") != -1;TEST _result_refScan_referenzName NOT_ATTRIBUTE_IS_MISSING _FME_BLANK_STRING_'@Value(_result_refScan_referenzName)'BOOL_OP;AND;COMPOSITE_TEST;<Unused>;TEST @FindString(@Value(gml_id),"XPLAN_XP_RASTERPLANBASIS") != -1;TEST _result_refScan_referenzName ATTRIBUTE_IS_MISSING _FME_BLANK_STRING_'default'FME_NUM_CONDITIONS3___
      SET_TO planDocument.DocumentCitation.shortName = FME_CONDITIONAL:DEFAULT_VALUE'_FME_NO_OP_'BOOL_OP;OR;COMPOSITE_TEST;<Unused>;TEST @FindString(@Value(gml_id),"XPLAN_XP_RASTERPLANBASIS") != -1'Rasterdarstellung'FME_NUM_CONDITIONS2___
      SET_TO planDocument.DocumentCitation.date.CI_Date.date.Date = FME_CONDITIONAL:DEFAULT_VALUE'_FME_NO_OP_'BOOL_OP;AND;COMPOSITE_TEST;<Unused>;TEST @FindString(@Value(gml_id),"XPLAN_XP_RASTERPLANBASIS") != -1;TEST _result_refScan_datum NOT_ATTRIBUTE_IS_MISSING _FME_BLANK_STRING_'@Value(_result_refScan_datum)'FME_NUM_CONDITIONS2___
      SET_TO planDocument.DocumentCitation.date.CI_Date.dateType.CI_DateTypeCode = FME_CONDITIONAL:DEFAULT_VALUE'_FME_NO_OP_'BOOL_OP;AND;COMPOSITE_TEST;<Unused>;TEST @FindString(@Value(gml_id),"XPLAN_XP_RASTERPLANBASIS") != -1;TEST _result_refScan_datum NOT_ATTRIBUTE_IS_MISSING _FME_BLANK_STRING_'creation'FME_NUM_CONDITIONS2___
      SET_TO planDocument.DocumentCitation.date.CI_Date.dateType.CI_DateTypeCode.codeList = FME_CONDITIONAL:DEFAULT_VALUE'_FME_NO_OP_'BOOL_OP;AND;COMPOSITE_TEST;<Unused>;TEST @FindString(@Value(gml_id),"XPLAN_XP_RASTERPLANBASIS") != -1;TEST _result_refScan_datum NOT_ATTRIBUTE_IS_MISSING _FME_BLANK_STRING_'http://www.isotc211.org/2005/resources/Codelist/gmxCodelists.xml#CI_DateTypeCode'FME_NUM_CONDITIONS2___
      SET_TO planDocument.DocumentCitation.date.CI_Date.dateType.CI_DateTypeCode.codeListValue = FME_CONDITIONAL:DEFAULT_VALUE'_FME_NO_OP_'BOOL_OP;AND;COMPOSITE_TEST;<Unused>;TEST @FindString(@Value(gml_id),"XPLAN_XP_RASTERPLANBASIS") != -1;TEST _result_refScan_datum NOT_ATTRIBUTE_IS_MISSING _FME_BLANK_STRING_'creation'FME_NUM_CONDITIONS2___
      SET_TO _planDocument.DocumentCitation.link{0}
      SET_TO _planDocument.DocumentCitation.link{0}.nilReason
      SET_TO _planDocument.DocumentCitation.link{0}.xsi_nil
    -> OfficialDocumentation (writer INSPIRE_1) [off]
    -> OfficialDocumentation (writer INSPIRE_2)

Bookmark: gml geometry
GeometryReplacer_7
    KIND_LONG = GML
    SOURCE = @Value(_result_position)
    SRS_AXIS_ORDER_DISPLAY = Automatic
    REMOVE_ATTRIBUTE = Yes
    -> GeometryValidator
    <REJECTED> -> CenterPointReplacer
Note: for error Lines with only one point!
CenterPointReplacer
    MODE = Center Point
    POINT -> GeometryValidator
GeometryValidator
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    NAN_REMOVAL = NAN_REMOVAL
    SELF_INTERSECTING = SELF_INTERSECTING
    CHECK_HOLE_TOUCHING_POLYGON = No
    CONNECT_Z_MODE_TR = First Wins
    SUMMARY = Detailed
    ISSUE_ATTR_NAME = _issues
    NULL_REMOVAL = NULL_REMOVAL
    ARC_ENDPOINT_TOLERANCE_MODE = Auto
    REPAIR = Yes
    CONNECT_Z_MODE_SI = First Wins
    PRESETS = Custom
    TYPE_REPAIR = TYPE_REPAIR
    PASSED -> GeometryExtractor_4
    REPAIRED -> GeometryExtractor_4
GeometryExtractor_4
    OGCVERSION = 1.2
    KIND_LONG = OGC Well Known Binary
    REMOVE_GEOMETRY = Yes
    PREFER_POLYGON_OVER_SURFACE = Yes
    ATTR = _geometry_wkn
    -> GeometryReplacer_6
GeometryReplacer_6
    KIND_LONG = OGC Well Known Binary
    SOURCE = @Value(_geometry_wkn)
    ELLIPSOID_NAME = WGS84
    OUTPUT_POINT_DISPLAY = Point
    OGC_WKT_PRECISION_DISPLAY = 64-bit
    MSSQL_FORMAT_CHOICE = Geometry
    SRS_AXIS_ORDER_DISPLAY = Automatic
    REMOVE_ATTRIBUTE = Yes
    LETTERING = WGS84
    -> GeometryFilter
GeometryFilter
    GEOM_PORT_NAMES = Point Line Area
    BREAK_AGG = No
    POINT -> GeometryPropertySetter_4
    LINE -> GeometryPropertySetter_4
    AREA -> Orientor_3
Orientor_3
    KIND = RIGHT_HAND_RULE
    ORIENTED -> GeometryPropertySetter_4
GeometryPropertySetter_4
    OVERWRITE_CHOICE = Yes
    SETTYPE_PARAM = Geometry Name
    GEOM_NAME_FIELD = geometry
    SET -> CsmapReprojector_3
    SET -> SupplementaryRegulation (writer INSPIRE_1) [off]

FME custom transformer X2I_BPPlan_extract
This Transformer extracts all attributes from XPlan:BP_Plan for transformation into the INSPIRE PLU schema 4.0.
Parameters 
Binary Object: default binary_object
Gml Id: default gml_id 
Output 
gml_id
result... for single attributes
results_list... for list attributes

Parameters:
- BINARY_OBJECT = @Value(binary_object)   # Binary Object
- GML_ID = @Value(gml_id)   # Gml Id

X2I_BPPlan_extract_Input (input)
    -> TextDecoder
X2I_BPPlan_extract_Output (output)

Bookmark: XPLan:BP_Plan
TextDecoder
    STRING_TO_DECODE = @Value(binary_object)
    DEST_ATTR = _decoded
    ENCODING_TYPE = HEX
    ATTR_ENCODING = utf-8
    -> XMLFormatter
XMLFormatter
    NAMESPACE_CLEANUP = No
    COLLAPSE_EMPTY_ELEMENT = No
    FORMATTING_CHOICE = Pretty-Print XML
    XML_OUTPUT_ATTR = _xml_output
    OUTPUT_ENCODING = utf-8
    REMOVE_ALL_COMMENT = No
    WHITESPACE_HANDLING = Preserve all whitespace
    SCHEMALOC_CLEANUP = No
    XML_OUTPUT_TYPE = Attribute
    XML_INPUT_TYPE = Attribute Specifying XML Text
    XML_ATTR_TEXT = _decoded
    REMOVE_EMPTY_ELEMENT = No
    TEXT_INDENT = no
    LIST_NAME = _xml_error
    INDENT_SIZE = 1
    REPLACE_TABS_WITH_SPACES = no
    PASSED -> XMLXQueryExtractor_2
Note: xplan:raeumlicherGeltungsbereich
XMLXQueryExtractor_2
    XQUERY_TYPE = XQuery expression
    RESULT_TYPE_NAME = Single value
    WRITE_XML_HEADER = No
    RESULT_ATTRIBUTE = _result_raeumlicherGeltungsbereich
    XML_ATTR = _xml_output
    QUERY_EXPR:
      declare namespace xplan="http://www.xplanung.de/xplangml/4/1";
      declare namespace gml="http://www.opengis.net/gml/3.2";
      //xplan:raeumlicherGeltungsbereich/*
    XML_REMOVE_SOURCE_ATTR = No
    XML_TYPE = Attribute specifying XML
    QUERY_RESULTS -> XMLXQueryExtractor_8
Note: xplan:name
XMLXQueryExtractor_8
    XQUERY_TYPE = XQuery expression
    RESULT_TYPE_NAME = Single value
    WRITE_XML_HEADER = No
    RESULT_ATTRIBUTE = _result_name
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:name)}
    XML_REMOVE_SOURCE_ATTR = No
    XML_TYPE = Attribute specifying XML
    QUERY_RESULTS -> XMLXQueryExtractor_9
Note: xplan:planArt (list)
XMLXQueryExtractor_9
    XQUERY_TYPE = XQuery expression
    RESULT_TYPE_NAME = List attribute
    WRITE_XML_HEADER = No
    LIST_RESULT_ATTR = _results_list_planArt
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:planArt)}
    XML_REMOVE_SOURCE_ATTR = No
    XML_TYPE = Attribute specifying XML
    QUERY_RESULTS -> XMLXQueryExtractor_10
Note: xplan:rechtsstand
XMLXQueryExtractor_10
    XQUERY_TYPE = XQuery expression
    RESULT_TYPE_NAME = Single value
    WRITE_XML_HEADER = No
    RESULT_ATTRIBUTE = _result_rechtsstand
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:rechtsstand)}
    XML_REMOVE_SOURCE_ATTR = No
    XML_TYPE = Attribute specifying XML
    QUERY_RESULTS -> XMLXQueryExtractor_11
Note: xplan:technHerstellDatum
XMLXQueryExtractor_11
    XQUERY_TYPE = XQuery expression
    RESULT_TYPE_NAME = Single value
    WRITE_XML_HEADER = No
    RESULT_ATTRIBUTE = _result_technHerstellDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:technHerstellDatum)}
    XML_REMOVE_SOURCE_ATTR = No
    XML_TYPE = Attribute specifying XML
    QUERY_RESULTS -> XMLXQueryExtractor_12
Note: xplan:rechtsverordnungsDatum
XMLXQueryExtractor_12
    XQUERY_TYPE = XQuery expression
    RESULT_TYPE_NAME = Single value
    WRITE_XML_HEADER = No
    RESULT_ATTRIBUTE = _result_rechtsverordnungsDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:rechtsverordnungsDatum)}
    XML_REMOVE_SOURCE_ATTR = No
    XML_TYPE = Attribute specifying XML
    QUERY_RESULTS -> XMLXQueryExtractor_3
Note: xplan:bereich (list)
XMLXQueryExtractor_3
    XQUERY_TYPE = XQuery expression
    RESULT_TYPE_NAME = List attribute
    WRITE_XML_HEADER = No
    LIST_RESULT_ATTR = _results_list_bereich
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:bereich/@xlink:href)}
    XML_REMOVE_SOURCE_ATTR = No
    XML_TYPE = Attribute specifying XML
    QUERY_RESULTS -> XMLXQueryExtractor_5
Note: xplan:texte (list)
XMLXQueryExtractor_5
    XQUERY_TYPE = XQuery expression
    RESULT_TYPE_NAME = List attribute
    WRITE_XML_HEADER = No
    LIST_RESULT_ATTR = _results_list_texte
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:texte/@xlink:href)}
    XML_REMOVE_SOURCE_ATTR = No
    XML_TYPE = Attribute specifying XML
    QUERY_RESULTS -> XMLXQueryExtractor_6
Note: xplan:begruendungsTexte (list)
XMLXQueryExtractor_6
    XQUERY_TYPE = XQuery expression
    RESULT_TYPE_NAME = List attribute
    WRITE_XML_HEADER = No
    LIST_RESULT_ATTR = _results_list_begruendungstexte
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:begruendungsTexte/@xlink:href)}
    XML_REMOVE_SOURCE_ATTR = No
    XML_TYPE = Attribute specifying XML
    QUERY_RESULTS -> XMLXQueryExtractor_4
Note: xplan:nummer
XMLXQueryExtractor_4
    XQUERY_TYPE = XQuery expression
    RESULT_TYPE_NAME = Single value
    WRITE_XML_HEADER = No
    RESULT_ATTRIBUTE = _result_nummer
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:nummer)}
    XML_REMOVE_SOURCE_ATTR = No
    XML_TYPE = Attribute specifying XML
    QUERY_RESULTS -> XMLXQueryExtractor_7
Note: xplan:genehmigungsDatum
XMLXQueryExtractor_7
    XQUERY_TYPE = XQuery expression
    RESULT_TYPE_NAME = Single value
    WRITE_XML_HEADER = No
    RESULT_ATTRIBUTE = _result_genehmigungsDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:genehmigungsDatum)}
    XML_REMOVE_SOURCE_ATTR = No
    XML_TYPE = Attribute specifying XML
    QUERY_RESULTS -> XMLXQueryExtractor_13
Note: xplan:untergangsDatum
XMLXQueryExtractor_13
    XQUERY_TYPE = XQuery expression
    RESULT_TYPE_NAME = Single value
    WRITE_XML_HEADER = No
    RESULT_ATTRIBUTE = _result_untergangsDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:untergangsDatum)}
    XML_REMOVE_SOURCE_ATTR = No
    XML_TYPE = Attribute specifying XML
    QUERY_RESULTS -> XMLXQueryExtractor_14
Note: xplan:hatGenerAttribut (list)
XMLXQueryExtractor_14
    XQUERY_TYPE = XQuery expression
    RESULT_TYPE_NAME = List attribute
    WRITE_XML_HEADER = No
    LIST_RESULT_ATTR = _results_list_hatGenerAttribut
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:hatGenerAttribut)}
    XML_REMOVE_SOURCE_ATTR = No
    XML_TYPE = Attribute specifying XML
    QUERY_RESULTS -> XMLXQueryExtractor_16
    QUERY_RESULTS -> XMLXQueryExtractor_15 [off]
Note: xplan:externeReferenz (list) ab 5.0
XMLXQueryExtractor_15 [off]
    XQUERY_TYPE = XQuery expression
    RESULT_TYPE_NAME = List attribute
    WRITE_XML_HEADER = No
    LIST_RESULT_ATTR = _results_list_externeReferenz
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:externeReferenz/@xlink:href)}
    XML_REMOVE_SOURCE_ATTR = No
    XML_TYPE = Attribute specifying XML
    QUERY_RESULTS -> XMLXQueryExtractor_16 [off]
Note: xplan:aenderungenBisDatum
XMLXQueryExtractor_16
    XQUERY_TYPE = XQuery expression
    RESULT_TYPE_NAME = Single value
    WRITE_XML_HEADER = No
    RESULT_ATTRIBUTE = _result_aenderungenBisDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:aenderungenBisDatum)}
    XML_REMOVE_SOURCE_ATTR = No
    XML_TYPE = Attribute specifying XML
    QUERY_RESULTS -> XMLXQueryExtractor_17
Note: xplan:aufstellungsbeschlussDatum
XMLXQueryExtractor_17
    XQUERY_TYPE = XQuery expression
    RESULT_TYPE_NAME = Single value
    WRITE_XML_HEADER = No
    RESULT_ATTRIBUTE = _result_aufstellungsbeschlussDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:aufstellungsbeschlussDatum)}
    XML_REMOVE_SOURCE_ATTR = No
    XML_TYPE = Attribute specifying XML
    QUERY_RESULTS -> XMLXQueryExtractor_18
Note: xplan:veraenderungssperreDatum
XMLXQueryExtractor_18
    XQUERY_TYPE = XQuery expression
    RESULT_TYPE_NAME = Single value
    WRITE_XML_HEADER = No
    RESULT_ATTRIBUTE = _result_veraenderungssperreDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:veraenderungssperreDatum)}
    XML_REMOVE_SOURCE_ATTR = No
    XML_TYPE = Attribute specifying XML
    QUERY_RESULTS -> XMLXQueryExtractor_19
Note: xplan:auslegungsStartDatum (list)
XMLXQueryExtractor_19
    XQUERY_TYPE = XQuery expression
    RESULT_TYPE_NAME = List attribute
    WRITE_XML_HEADER = No
    LIST_RESULT_ATTR = _results_list_auslegungsStartDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:auslegungsStartDatum)}
    XML_REMOVE_SOURCE_ATTR = No
    XML_TYPE = Attribute specifying XML
    QUERY_RESULTS -> XMLXQueryExtractor_20
Note: xplan:auslegungsEndDatum (list)
XMLXQueryExtractor_20
    XQUERY_TYPE = XQuery expression
    RESULT_TYPE_NAME = List attribute
    WRITE_XML_HEADER = No
    LIST_RESULT_ATTR = _results_list_auslegungsEndDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:auslegungsEndDatum)}
    XML_REMOVE_SOURCE_ATTR = No
    XML_TYPE = Attribute specifying XML
    QUERY_RESULTS -> XMLXQueryExtractor_21
Note: xplan:traegerbeteiligungsStartDatum (list)
XMLXQueryExtractor_21
    XQUERY_TYPE = XQuery expression
    RESULT_TYPE_NAME = List attribute
    WRITE_XML_HEADER = No
    LIST_RESULT_ATTR = _results_list_traegerbeteiligungsStartDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:traegerbeteiligungsStartDatum)}
    XML_REMOVE_SOURCE_ATTR = No
    XML_TYPE = Attribute specifying XML
    QUERY_RESULTS -> XMLXQueryExtractor_22
Note: xplan:traegerbeteiligungsStartDatum (list)
XMLXQueryExtractor_22
    XQUERY_TYPE = XQuery expression
    RESULT_TYPE_NAME = List attribute
    WRITE_XML_HEADER = No
    LIST_RESULT_ATTR = _results_list_traegerbeteiligungsEndDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x//xplan:traegerbeteiligungsEndDatum)}
    XML_REMOVE_SOURCE_ATTR = No
    XML_TYPE = Attribute specifying XML
    QUERY_RESULTS -> XMLXQueryExtractor_23
Note: xplan:satzungsbeschlussDatum
XMLXQueryExtractor_23
    XQUERY_TYPE = XQuery expression
    RESULT_TYPE_NAME = Single value
    WRITE_XML_HEADER = No
    RESULT_ATTRIBUTE = _result_satzungsbeschlussDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:satzungsbeschlussDatum)}
    XML_REMOVE_SOURCE_ATTR = No
    XML_TYPE = Attribute specifying XML
    QUERY_RESULTS -> XMLXQueryExtractor_24
Note: xplan:inkrafttretensDatum
XMLXQueryExtractor_24
    XQUERY_TYPE = XQuery expression
    RESULT_TYPE_NAME = Single value
    WRITE_XML_HEADER = No
    RESULT_ATTRIBUTE = _result_inkrafttretensDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:inkrafttretensDatum)}
    XML_REMOVE_SOURCE_ATTR = No
    XML_TYPE = Attribute specifying XML
    QUERY_RESULTS -> XMLXQueryExtractor_25
Note: xplan:ausfertigungsDatum
XMLXQueryExtractor_25
    XQUERY_TYPE = XQuery expression
    RESULT_TYPE_NAME = Single value
    WRITE_XML_HEADER = No
    RESULT_ATTRIBUTE = _result_ausfertigungsDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Plan
          return {data($x/xplan:ausfertigungsDatum)}
    XML_REMOVE_SOURCE_ATTR = No
    XML_TYPE = Attribute specifying XML
    QUERY_RESULTS -> Tester
Tester
    BOOL_OP = OR
    TEST_MODE = Automatic
    TEST_CLAUSE = TEST _result_raeumlicherGeltungsbereich NOT_ATTRIBUTE_IS_MISSING ""
    TEST_DESCRIPTION = ""
    PASSED -> AttributeRemover
AttributeRemover
    REMOVE_ATTRS = _decoded,binary_object,_xml_output
    -> X2I_BPPlan_extract_Output (output)

FME custom transformer X2I_spatialPlan_ordinanceList_create
This Transformer creates the ordinace List for plu:SpatialPlan (schema 4.0).
Parameters 
all
Output
all

Parameters:
- _RESULT_AENDERUNGENBISDATUM = @Value(_result_aenderungenBisDatum)   # Result Aenderungenbisdatum
- _RESULT_AUFSTELLUNGSBESCHLUSSDATUM = @Value(_result_aufstellungsbeschlussDatum)   # Result Aufstellungsbeschlussdatum
- _RESULT_AUSFERTIGUNGSDATUM = @Value(_result_ausfertigungsDatum)   # Result Ausfertigungsdatum
- _RESULT_GENEHMIGUNGSDATUM = @Value(_result_genehmigungsDatum)   # Result Genehmigungsdatum
- _RESULT_RECHTSVERORDNUNGSDATUM = @Value(_result_rechtsverordnungsDatum)   # Result Rechtsverordnungsdatum
- _RESULT_SATZUNGSBESCHLUSSDATUM = @Value(_result_satzungsbeschlussDatum)   # Result Satzungsbeschlussdatum
- _RESULT_TECHNHERSTELLDATUM = @Value(_result_technHerstellDatum)   # Result Technherstelldatum
- _RESULT_VERAENDERUNGSSPERREDATUM = @Value(_result_veraenderungssperreDatum)   # Result Veraenderungssperredatum

X2I_spatialPlan_ordinanceList_create_Input (input)
    -> Tester_3
X2I_spatialPlan_ordinanceList_create_Output (output)

Bookmark: create_spatialPlan_ordinanceList
Tester_3
    BOOL_OP = AND
    TEST_MODE = Automatic
    TEST_CLAUSE:
      TEST _result_technHerstellDatum NOT_ATTRIBUTE_IS_MISSING ""
      TEST _result_technHerstellDatum NOT_ATTRIBUTE_VALUE_NULL ""
    TEST_DESCRIPTION = ""
    PASSED -> DateTimeConverter
    FAILED -> Tester_4
DateTimeConverter
    REPAIR_INPUT = YES
    OUT_FORMAT = %Y-%m-%dT%H:%M:%S
    DATETIME_ATTR = _result_technHerstellDatum
    IN_FORMAT = %Y-%m-%d$
    -> Tester_4
Tester_4
    BOOL_OP = AND
    TEST_MODE = Automatic
    TEST_CLAUSE:
      TEST _result_rechtsverordnungsDatum NOT_ATTRIBUTE_IS_MISSING ""
      TEST _result_rechtsverordnungsDatum NOT_ATTRIBUTE_VALUE_NULL ""
    TEST_DESCRIPTION = ""
    PASSED -> DateTimeConverter_2
    FAILED -> Tester_2
DateTimeConverter_2
    REPAIR_INPUT = YES
    OUT_FORMAT = %Y-%m-%dT%H:%M:%S
    DATETIME_ATTR = _result_rechtsverordnungsDatum
    IN_FORMAT = %Y-%m-%d$
    -> Tester_2
Tester_2
    BOOL_OP = AND
    TEST_MODE = Automatic
    TEST_CLAUSE:
      TEST _result_genehmigungsDatum NOT_ATTRIBUTE_IS_MISSING ""
      TEST _result_genehmigungsDatum NOT_ATTRIBUTE_VALUE_NULL ""
    TEST_DESCRIPTION = ""
    PASSED -> DateTimeConverter_3
    FAILED -> Tester_5
DateTimeConverter_3
    REPAIR_INPUT = YES
    OUT_FORMAT = %Y-%m-%dT%H:%M:%S
    DATETIME_ATTR = _result_genehmigungsDatum
    IN_FORMAT = %Y-%m-%d$
    -> Tester_5
Tester_5
    BOOL_OP = AND
    TEST_MODE = Automatic
    TEST_CLAUSE:
      TEST _result_aenderungenBisDatum NOT_ATTRIBUTE_IS_MISSING ""
      TEST _result_aenderungenBisDatum NOT_ATTRIBUTE_VALUE_NULL ""
    TEST_DESCRIPTION = ""
    PASSED -> DateTimeConverter_4
    FAILED -> Tester_6
DateTimeConverter_4
    REPAIR_INPUT = YES
    OUT_FORMAT = %Y-%m-%dT%H:%M:%S
    DATETIME_ATTR = _result_aenderungenBisDatum
    IN_FORMAT = %Y-%m-%d$
    -> Tester_6
Tester_6
    BOOL_OP = AND
    TEST_MODE = Automatic
    TEST_CLAUSE:
      TEST _result_aufstellungsbeschlussDatum NOT_ATTRIBUTE_IS_MISSING ""
      TEST _result_aufstellungsbeschlussDatum NOT_ATTRIBUTE_VALUE_NULL ""
    TEST_DESCRIPTION = ""
    PASSED -> DateTimeConverter_5
    FAILED -> Tester_7
DateTimeConverter_5
    REPAIR_INPUT = YES
    OUT_FORMAT = %Y-%m-%dT%H:%M:%S
    DATETIME_ATTR = _result_aufstellungsbeschlussDatum
    IN_FORMAT = %Y-%m-%d$
    -> Tester_7
Tester_7
    BOOL_OP = AND
    TEST_MODE = Automatic
    TEST_CLAUSE:
      TEST _result_veraenderungssperreDatum NOT_ATTRIBUTE_IS_MISSING ""
      TEST _result_veraenderungssperreDatum NOT_ATTRIBUTE_VALUE_NULL ""
    TEST_DESCRIPTION = ""
    PASSED -> DateTimeConverter_6
    FAILED -> Tester_8
DateTimeConverter_6
    REPAIR_INPUT = YES
    OUT_FORMAT = %Y-%m-%dT%H:%M:%S
    DATETIME_ATTR = _result_veraenderungssperreDatum
    IN_FORMAT = %Y-%m-%d$
    -> Tester_8
Tester_8
    BOOL_OP = AND
    TEST_MODE = Automatic
    TEST_CLAUSE:
      TEST _result_satzungsbeschlussDatum NOT_ATTRIBUTE_IS_MISSING ""
      TEST _result_satzungsbeschlussDatum NOT_ATTRIBUTE_VALUE_NULL ""
    TEST_DESCRIPTION = ""
    PASSED -> DateTimeConverter_7
    FAILED -> Tester_9
DateTimeConverter_7
    REPAIR_INPUT = YES
    OUT_FORMAT = %Y-%m-%dT%H:%M:%S
    DATETIME_ATTR = _result_satzungsbeschlussDatum
    IN_FORMAT = %Y-%m-%d$
    -> Tester_9
Tester_9
    BOOL_OP = AND
    TEST_MODE = Automatic
    TEST_CLAUSE:
      TEST _result_ausfertigungsDatum NOT_ATTRIBUTE_IS_MISSING ""
      TEST _result_ausfertigungsDatum NOT_ATTRIBUTE_VALUE_NULL ""
    TEST_DESCRIPTION = ""
    PASSED -> DateTimeConverter_8
    FAILED -> PythonCaller_2
DateTimeConverter_8
    REPAIR_INPUT = YES
    OUT_FORMAT = %Y-%m-%dT%H:%M:%S
    DATETIME_ATTR = _result_ausfertigungsDatum
    IN_FORMAT = %Y-%m-%d$
    -> PythonCaller_2
PythonCaller_2
    PYTHONSOURCE:
      import fme
      import fmeobjects
      import datetime

      def createOrdinanceList(feature):
          technHerstellDatum = feature.getAttribute("_result_technHerstellDatum")
          rechtsverordnungsDatum = feature.getAttribute("_result_rechtsverordnungsDatum")
          genehmigungsDatum = feature.getAttribute('_result_genehmigungsDatum')
          aenderungenBisDatum = feature.getAttribute('_result_aenderungenBisDatum')
          aufstellungsbeschlussDatum = feature.getAttribute('_result_aufstellungsbeschlussDatum')
          veraenderungssperreDatum = feature.getAttribute('_result_veraenderungssperreDatum')
          satzungsbeschlussDatum = feature.getAttribute('_result_satzungsbeschlussDatum')
          ausfertigungsDatum = feature.getAttribute('_result_ausfertigungsDatum')

          listAuslegungsStartDatum = feature.getAttribute("_results_list_auslegungsStartDatum{}")
          listAuslegungsEndDatum = feature.getAttribute("_results_list_auslegungsEndDatum{}")
          listTraegerbeteiligungsStartDatum = feature.getAttribute("_results_list_traegerbeteiligungsStartDatum{}")
          listTraegerbeteiligungsEndDatum = feature.getAttribute("_results_list_traegerbeteiligungsEndDatum{}")

          listOrdinanceDate = []
          listOrdinanceRef = []

          if technHerstellDatum:
              listOrdinanceDate.append(technHerstellDatum)
              listOrdinanceRef.append("technHerstellDatum")

          if rechtsverordnungsDatum:
              listOrdinanceDate.append(rechtsverordnungsDatum)
              listOrdinanceRef.append("rechtsverordnungsDatum")

          if genehmigungsDatum:
              listOrdinanceDate.append(genehmigungsDatum)
              listOrdinanceRef.append("genehmigungsDatum")

          if aenderungenBisDatum:
              listOrdinanceDate.append(aenderungenBisDatum)
              listOrdinanceRef.append("aenderungenBisDatum")

          if aufstellungsbeschlussDatum:
              listOrdinanceDate.append(aufstellungsbeschlussDatum)
              listOrdinanceRef.append("aufstellungsbeschlussDatum")

          if veraenderungssperreDatum:
              listOrdinanceDate.append(veraenderungssperreDatum)
              listOrdinanceRef.append("veraenderungssperreDatum")

          if satzungsbeschlussDatum:
              listOrdinanceDate.append(satzungsbeschlussDatum)
              listOrdinanceRef.append("satzungsbeschlussDatum")

          if ausfertigungsDatum:
              listOrdinanceDate.append(ausfertigungsDatum)
              listOrdinanceRef.append("ausfertigungsDatum")

          if listAuslegungsStartDatum:
              for i in range(len(listAuslegungsStartDatum)):
                  objDate = datetime.datetime.strptime(listAuslegungsStartDatum[i], "%Y-%m-%d")
                  strDate = datetime.datetime.strftime(objDate, "%Y-%m-%dT%H:%M:%S")
                  listOrdinanceDate.append(strDate)
                  listOrdinanceRef.append("auslegungsStartDatum")

          if listAuslegungsEndDatum:
              for i in range(len(listAuslegungsEndDatum)):
                  objDate = datetime.datetime.strptime(listAuslegungsEndDatum[i], "%Y-%m-%d")
                  strDate = datetime.datetime.strftime(objDate, "%Y-%m-%dT%H:%M:%S")
                  listOrdinanceDate.append(strDate)
                  listOrdinanceRef.append("auslegungsEndDatum")

          if listTraegerbeteiligungsStartDatum:
              for i in range(len(listTraegerbeteiligungsStartDatum)):
                  objDate = datetime.datetime.strptime(listTraegerbeteiligungsStartDatum[i], "%Y-%m-%d")
                  strDate = datetime.datetime.strftime(objDate, "%Y-%m-%dT%H:%M:%S")
                  listOrdinanceDate.append(strDate)
                  listOrdinanceRef.append("traegerbeteiligungsStartDatum")

          if listTraegerbeteiligungsEndDatum:
              for i in range(len(listTraegerbeteiligungsEndDatum)):
                  objDate = datetime.datetime.strptime(listTraegerbeteiligungsEndDatum[i], "%Y-%m-%d")
                  strDate = datetime.datetime.strftime(objDate, "%Y-%m-%dT%H:%M:%S")
                  listOrdinanceDate.append(strDate)
                  listOrdinanceRef.append("traegerbeteiligungsEndDatum")

          if len(listOrdinanceDate) > 0:
              for i in range(len(listOrdinanceDate)):
                  attrName1 = "ordinance{" + str(i) + "}.OrdinanceValue.ordinanceDate"
                  attrName2 = "ordinance{" + str(i) + "}.OrdinanceValue.ordinanceReference"
                  feature.setAttribute(attrName1,listOrdinanceDate[i])
                  feature.setAttribute(attrName2,listOrdinanceRef[i])
          else:
              attrName1 = "ordinance{0}.nilReason"
              attrName2 = "ordinance{0}.xsi_nil"
              feature.setAttribute(attrName1,"other:unpopulated")
              feature.setAttribute(attrName2,"true")
    PYTHONSYMBOL = createOrdinanceList
    -> X2I_spatialPlan_ordinanceList_create_Output (output)

FME custom transformer X2I_XPlanBaseClasses_filter
This Transformer splits objects from _results_list_inhaltBPlan{} into plu: ZoningElement and plu: SupplementaryRegulation (schema 4.0).
Parameters 
_results_list_inhaltBPlan{}
Output 1: X2I_XPlanBaseClasses_filter_memberList_Output 
_result_gehoertZuBP_Bereich
_list_member{}
Output 2: X2I_XPlanBaseClasses_filter_restrictionList_Output 
_result_gehoertZuBP_Bereich
_list_restriction{}
Output 3: X2I_XPlanBaseClasses_filter_memberPassed_Output 
gml_id
_xml_output
_result... for single attributes
Output 4: X2I_XPlanBaseClasses_filter_restrictionPassed_Output 
gml_id
_xml_output
_result... for single attributes

X2I_XPlanBaseClasses_filter_Input (input)
    -> PythonCaller_Select_inhaltBPlan_41
X2I_XPlanBaseClasses_filter_memberList_Output (output)
X2I_XPlanBaseClasses_filter_restrictionList_Output (output)
X2I_XPlanBaseClasses_filter_restrictionPassed_Output (output)
X2I_XPlanBaseClasses_filter_memberPassed_Output (output)

Bookmark: SQL Statement Zuordnung zoning or restriction
PythonCaller_Select_inhaltBPlan_41
    PYTHONSOURCE:
      import fme
      import fmeobjects

      def createBPlanInhaltSqlScript(feature):
          listBereichInhalt = feature.getAttribute("_results_list_inhaltBPlan{}")
          listNachrichtlich = feature.getAttribute("_results_list_nachrichtlich{}")

          if listBereichInhalt:
              if listNachrichtlich:
                  for i, element in enumerate(listNachrichtlich):
                      listBereichInhalt.append(element)

              sqlStrFull = "SELECT gml_id, ft_type, binary_object FROM xplan41.gml_objects WHERE gml_id LIKE '"
              sqlStrOr = "' OR gml_id LIKE '"
              sqlStrEnd = "';"

              for i in range(len(listBereichInhalt)):
                  if i == 0:
                      docRef = listBereichInhalt[i].replace("#", "")
                      sqlStrFull += docRef
                  else:
                      sqlStrFull += sqlStrOr
                      docRef = listBereichInhalt[i].replace("#", "")
                      sqlStrFull += docRef

              sqlStrFull += sqlStrEnd
              feature.setAttribute("bPlanInhaltSqlScript",sqlStrFull)
    NEW_ATTRIBUTES = bPlanInhaltSqlScript
    PYTHONSYMBOL = createBPlanInhaltSqlScript
    -> SQLExecutor_5 [INITIATOR]
SQLExecutor_5
    EXPOSED_ATTRIBUTE_LIST = binary_object,gml_id
    COMBINE_ATTRS = Result Attributes Only
    COMBINE_GEOM = Initiator Geometry Only
    POSTGRES_SCHEMAS_FOR_TABLE_LISTING = xplan41
    SQL_STATEMENT = @Value(bPlanInhaltSqlScript)
    POSTGRES_NAMED_CONNECTION = maske_xplan4.1-test
    DATASET = maske_xplan4.1-test
    POSTGRES_QUERY_FEATURE_TYPES_FOR_MERGE_FILTERS = Yes
    FORMAT = POSTGRES
    RESULT -> TextDecoder_6
    <REJECTED> -> SQLExecutor_5__Rejected_
SQLExecutor_5__Rejected_: Inspector [off]
TextDecoder_6
    STRING_TO_DECODE = @Value(binary_object)
    DEST_ATTR = _decoded
    ENCODING_TYPE = HEX
    ATTR_ENCODING = utf-8
    -> XMLFormatter_6
XMLFormatter_6
    NAMESPACE_CLEANUP = No
    COLLAPSE_EMPTY_ELEMENT = No
    FORMATTING_CHOICE = Pretty-Print XML
    XML_OUTPUT_ATTR = _xml_output
    OUTPUT_ENCODING = utf-8
    REMOVE_ALL_COMMENT = No
    WHITESPACE_HANDLING = Preserve all whitespace
    SCHEMALOC_CLEANUP = No
    XML_OUTPUT_TYPE = Attribute
    XML_INPUT_TYPE = Attribute Specifying XML Text
    XML_ATTR_TEXT = _decoded
    REMOVE_EMPTY_ELEMENT = No
    TEXT_INDENT = no
    LIST_NAME = _xml_error
    INDENT_SIZE = 1
    REPLACE_TABS_WITH_SPACES = no
    PASSED -> XMLXQueryExtractor_13
Note: xplan:ebene
XMLXQueryExtractor_13
    XQUERY_TYPE = XQuery expression
    RESULT_TYPE_NAME = Single value
    WRITE_XML_HEADER = No
    RESULT_ATTRIBUTE = _result_ebene
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:ebene)}
    XML_REMOVE_SOURCE_ATTR = No
    XML_TYPE = Attribute specifying XML
    QUERY_RESULTS -> XMLXQueryExtractor_14
Note: xplan:flaechenschluss
XMLXQueryExtractor_14
    XQUERY_TYPE = XQuery expression
    RESULT_TYPE_NAME = Single value
    WRITE_XML_HEADER = No
    RESULT_ATTRIBUTE = _result_flaechenschluss
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:flaechenschluss)}
    XML_REMOVE_SOURCE_ATTR = No
    XML_TYPE = Attribute specifying XML
    QUERY_RESULTS -> XMLXQueryExtractor_15
Note: xplan:gehoertZuBP_Bereich bis 4.1
XMLXQueryExtractor_15
    XQUERY_TYPE = XQuery expression
    RESULT_TYPE_NAME = Single value
    WRITE_XML_HEADER = No
    RESULT_ATTRIBUTE = _result_gehoertZuBP_Bereich
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:gehoertZuBP_Bereich/@xlink:href)}
    XML_REMOVE_SOURCE_ATTR = No
    XML_TYPE = Attribute specifying XML
    QUERY_RESULTS -> XMLXQueryExtractor_2 [off]
    QUERY_RESULTS -> XMLXQueryExtractor_3
Note: xplan:gehoertZuBereich ab 5.0
XMLXQueryExtractor_2 [off]
    XQUERY_TYPE = XQuery expression
    RESULT_TYPE_NAME = Single value
    WRITE_XML_HEADER = No
    RESULT_ATTRIBUTE = _result_gehoertZuBereich
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:gehoertZuBereich/@xlink:href)}
    XML_REMOVE_SOURCE_ATTR = No
    XML_TYPE = Attribute specifying XML
    QUERY_RESULTS -> XMLXQueryExtractor_3 [off]
Note: xplan:gehoertNachrichtlichZuBereich bis 4.1
XMLXQueryExtractor_3
    XQUERY_TYPE = XQuery expression
    RESULT_TYPE_NAME = Single value
    WRITE_XML_HEADER = No
    RESULT_ATTRIBUTE = _result_gehoertNachrichtlichZuBereich
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:gehoertNachrichtlichZuBereich/@xlink:href)}
    XML_REMOVE_SOURCE_ATTR = No
    XML_TYPE = Attribute specifying XML
    QUERY_RESULTS -> Tester_3
Tester_3
    BOOL_OP = AND
    TEST_MODE = Automatic
    TEST_CLAUSE = TEST @Value(_result_gehoertNachrichtlichZuBereich) ATTRIBUTE_HAS_VALUE ""
    TEST_DESCRIPTION = ""
    PASSED -> AttributeCreator
    FAILED -> Tester
AttributeCreator
    ATTR_TABLE = SET_TO _result_gehoertZuBP_Bereich = @Value(_result_gehoertNachrichtlichZuBereich)
    -> Tester
Tester
    BOOL_OP = AND
    TEST_MODE = Automatic
    TEST_CLAUSE:
      TEST @Value(_result_flaechenschluss) = true
      TEST @Value(_result_ebene) = 0
    TEST_DESCRIPTION = ZoningElement
    PASSED -> Aggregator_2
    PASSED -> AttributeRemover
    FAILED -> Tester_21
Tester_21
    BOOL_OP = AND
    TEST_MODE = Automatic
    TEST_CLAUSE = TEST @Value(_result_flaechenschluss) = true
    TEST_DESCRIPTION = ZoningElement
    PASSED -> Aggregator_2
    PASSED -> AttributeRemover
    FAILED -> Tester_2
Aggregator_2
    SEP = ,
    ORDERED = No
    GROUP_BY = _result_gehoertZuBP_Bereich
    AGGREGATE_TYPE = Homogeneous Collection (If Possible)
    MODE = Geometry - Assemble One Level
    LIST_NAME = _list_member
    ACCUM_ATTRS_NAME = Use Attributes From One Feature
    LIST_ATTRS_TO_INCLUDE = gml_id
    AGGREGATE -> GeometryRemover
GeometryRemover
    -> AttributeRemover_memberList
AttributeRemover_memberList
    REMOVE_ATTRS = _result_ebene,binary_object,_decoded,_result_gehoertZuBereich,_xml_output,gml_id,_result_flaechenschluss
    -> X2I_XPlanBaseClasses_filter_memberList_Output (output)
Tester_2
    BOOL_OP = OR
    TEST_MODE = Automatic
    TEST_CLAUSE:
      TEST @Value(_result_flaechenschluss) = false
      TEST _result_flaechenschluss ATTRIBUTE_VALUE_NULL ""
      TEST _result_flaechenschluss ATTRIBUTE_IS_EMPTY ""
      TEST _result_flaechenschluss ATTRIBUTE_IS_MISSING ""
      TEST @Value(_result_ebene) > 0
    TEST_DESCRIPTION = ""
    PASSED -> Aggregator_3
    PASSED -> AttributeRemover_2
Aggregator_3
    SEP = ,
    ORDERED = No
    GROUP_BY = _result_gehoertZuBP_Bereich
    AGGREGATE_TYPE = Homogeneous Collection (If Possible)
    MODE = Geometry - Assemble One Level
    LIST_NAME = _list_restriction
    ACCUM_ATTRS_NAME = Use Attributes From One Feature
    LIST_ATTRS_TO_INCLUDE = gml_id
    AGGREGATE -> GeometryRemover_2
GeometryRemover_2
    -> AttributeRemover_restrictionList
AttributeRemover_restrictionList
    REMOVE_ATTRS = _result_ebene,binary_object,_decoded,_result_gehoertZuBereich,_xml_output,gml_id,_result_flaechenschluss
    -> X2I_XPlanBaseClasses_filter_restrictionList_Output (output)
AttributeRemover_2
    REMOVE_ATTRS = binary_object,_decoded
    -> X2I_XPlanBaseClasses_filter_restrictionPassed_Output (output)
AttributeRemover
    REMOVE_ATTRS = binary_object,_decoded
    -> X2I_XPlanBaseClasses_filter_memberPassed_Output (output)

FME custom transformer X2I_OfficialDocumentation_extract

Parameters:
- SQLSTRSTATEMENTOFFICIALDOCUMENT = @Value(sqlStrStatementOfficialDocument)   # sqlStrStatementOfficialDocument
- GML_ID = @Value(gml_id)   # Gml Id

X2I_OfficialDocumentation_extract_Input (input)
    -> SQLExecutor_2 [INITIATOR]
X2I_OfficialDocumentation_extract_Output (output)

Bookmark: plu:OfficialDocumentation
SQLExecutor_2
    EXPOSED_ATTRIBUTE_LIST = binary_object,gml_id
    COMBINE_ATTRS = Result Attributes Only
    COMBINE_GEOM = Initiator Geometry Only
    POSTGRES_SCHEMAS_FOR_TABLE_LISTING = xplan41
    SQL_STATEMENT = @Value(sqlStrStatementOfficialDocument)
    POSTGRES_NAMED_CONNECTION = maske_xplan4.1-test
    DATASET = maske_xplan4.1-test
    POSTGRES_QUERY_FEATURE_TYPES_FOR_MERGE_FILTERS = Yes
    FORMAT = POSTGRES
    RESULT -> TextDecoder_3
TextDecoder_3
    STRING_TO_DECODE = @Value(binary_object)
    DEST_ATTR = _decoded
    ENCODING_TYPE = HEX
    ATTR_ENCODING = utf-8
    -> XMLFormatter_3
XMLFormatter_3
    NAMESPACE_CLEANUP = No
    COLLAPSE_EMPTY_ELEMENT = No
    FORMATTING_CHOICE = Pretty-Print XML
    XML_OUTPUT_ATTR = _xml_output
    OUTPUT_ENCODING = utf-8
    REMOVE_ALL_COMMENT = No
    WHITESPACE_HANDLING = Preserve all whitespace
    SCHEMALOC_CLEANUP = No
    XML_OUTPUT_TYPE = Attribute
    XML_INPUT_TYPE = Attribute Specifying XML Text
    XML_ATTR_TEXT = _decoded
    REMOVE_EMPTY_ELEMENT = No
    TEXT_INDENT = no
    LIST_NAME = _xml_error
    INDENT_SIZE = 1
    REPLACE_TABS_WITH_SPACES = no
    PASSED -> GeometryRemover_3
GeometryRemover_3
    -> DuplicateFilter
Note: SpatialPlan und ZoningElement bzw. SupplementRegulation / können eine Referenz auf ein und dasselbe OfficialDocument / enthalten!
DuplicateFilter
    INPUT_ORDERED_CHOICE = No
    KEYATTR = gml_id
    UNIQUE -> XMLXQueryExtractor_39

Bookmark: TextAbschitt / BegruendungsAbschnitt
Note: xplan:text
XMLXQueryExtractor_39
    XQUERY_TYPE = XQuery expression
    RESULT_TYPE_NAME = Single value
    WRITE_XML_HEADER = No
    RESULT_ATTRIBUTE = _result_text
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:text)}
    XML_REMOVE_SOURCE_ATTR = No
    XML_TYPE = Attribute specifying XML
    QUERY_RESULTS -> XMLXQueryExtractor_41
Note: xplan:refText/xplan:XP_ExterneReferenz/xplan:datum
XMLXQueryExtractor_41
    XQUERY_TYPE = XQuery expression
    RESULT_TYPE_NAME = Single value
    WRITE_XML_HEADER = No
    RESULT_ATTRIBUTE = _result_refText_datum
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refText/xplan:XP_ExterneReferenz/xplan:datum)}
    XML_REMOVE_SOURCE_ATTR = No
    XML_TYPE = Attribute specifying XML
    QUERY_RESULTS -> XMLXQueryExtractor_2
Note: xplan:refText/xplan:XP_ExterneReferenz/xplan:georefURL
XMLXQueryExtractor_2
    XQUERY_TYPE = XQuery expression
    RESULT_TYPE_NAME = Single value
    WRITE_XML_HEADER = No
    RESULT_ATTRIBUTE = _result_refText_georefURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refText/xplan:XP_ExterneReferenz/xplan:georefURL)}
    XML_REMOVE_SOURCE_ATTR = No
    XML_TYPE = Attribute specifying XML
    QUERY_RESULTS -> XMLXQueryExtractor_3
Note: xplan:refText/xplan:XP_ExterneReferenz/xplan:referenzURL
XMLXQueryExtractor_3
    XQUERY_TYPE = XQuery expression
    RESULT_TYPE_NAME = Single value
    WRITE_XML_HEADER = No
    RESULT_ATTRIBUTE = _result_refText_referenzURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refText/xplan:XP_ExterneReferenz/xplan:referenzURL)}
    XML_REMOVE_SOURCE_ATTR = No
    XML_TYPE = Attribute specifying XML
    QUERY_RESULTS -> XMLXQueryExtractor_4
Note: xplan:refText/xplan:XP_ExterneReferenz/xplan:informationssystemURL
XMLXQueryExtractor_4
    XQUERY_TYPE = XQuery expression
    RESULT_TYPE_NAME = Single value
    WRITE_XML_HEADER = No
    RESULT_ATTRIBUTE = _result_refText_informationssystemURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refText/xplan:XP_ExterneReferenz/xplan:informationssystemURL)}
    XML_REMOVE_SOURCE_ATTR = No
    XML_TYPE = Attribute specifying XML
    QUERY_RESULTS -> XMLXQueryExtractor_5
Note: xplan:refText/xplan:XP_ExterneReferenz/xplan:referenzName
XMLXQueryExtractor_5
    XQUERY_TYPE = XQuery expression
    RESULT_TYPE_NAME = Single value
    WRITE_XML_HEADER = No
    RESULT_ATTRIBUTE = _result_refText_referenzName
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refText/xplan:XP_ExterneReferenz/xplan:referenzName)}
    XML_REMOVE_SOURCE_ATTR = No
    XML_TYPE = Attribute specifying XML
    QUERY_RESULTS -> XMLXQueryExtractor_6

Bookmark: XP_RasterPlanBasis ( bis 4.1) / XP_RasterDarstellung (ab 5.0)
Note: xplan:refScan/xplan:XP_ExterneReferenz/xplan:datum
XMLXQueryExtractor_6
    XQUERY_TYPE = XQuery expression
    RESULT_TYPE_NAME = Single value
    WRITE_XML_HEADER = No
    RESULT_ATTRIBUTE = _result_refScan_datum
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refScan/xplan:XP_ExterneReferenz/xplan:datum)}
    XML_REMOVE_SOURCE_ATTR = No
    XML_TYPE = Attribute specifying XML
    QUERY_RESULTS -> XMLXQueryExtractor_40
Note: xplan:refScan/xplan:XP_ExterneReferenz/xplan:georefURL
XMLXQueryExtractor_40
    XQUERY_TYPE = XQuery expression
    RESULT_TYPE_NAME = Single value
    WRITE_XML_HEADER = No
    RESULT_ATTRIBUTE = _result_refScan_georefURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refScan/xplan:XP_ExterneReferenz/xplan:georefURL)}
    XML_REMOVE_SOURCE_ATTR = No
    XML_TYPE = Attribute specifying XML
    QUERY_RESULTS -> XMLXQueryExtractor_42
Note: xplan:refScan/xplan:XP_ExterneReferenz/xplan:referenzURL
XMLXQueryExtractor_42
    XQUERY_TYPE = XQuery expression
    RESULT_TYPE_NAME = Single value
    WRITE_XML_HEADER = No
    RESULT_ATTRIBUTE = _result_refScan_referenzURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refScan/xplan:XP_ExterneReferenz/xplan:referenzURL)}
    XML_REMOVE_SOURCE_ATTR = No
    XML_TYPE = Attribute specifying XML
    QUERY_RESULTS -> XMLXQueryExtractor_7
Note: xplan:refScan/xplan:XP_ExterneReferenz/xplan:informationssystemURL
XMLXQueryExtractor_7
    XQUERY_TYPE = XQuery expression
    RESULT_TYPE_NAME = Single value
    WRITE_XML_HEADER = No
    RESULT_ATTRIBUTE = _result_refScan_informationssystemURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refScan/xplan:XP_ExterneReferenz/xplan:informationssystemURL)}
    XML_REMOVE_SOURCE_ATTR = No
    XML_TYPE = Attribute specifying XML
    QUERY_RESULTS -> XMLXQueryExtractor_8
Note: xplan:refScan/xplan:XP_ExterneReferenz/xplan:referenzName
XMLXQueryExtractor_8
    XQUERY_TYPE = XQuery expression
    RESULT_TYPE_NAME = Single value
    WRITE_XML_HEADER = No
    RESULT_ATTRIBUTE = _result_refScan_referenzName
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:refScan/xplan:XP_ExterneReferenz/xplan:referenzName)}
    XML_REMOVE_SOURCE_ATTR = No
    XML_TYPE = Attribute specifying XML
    QUERY_RESULTS -> XMLXQueryExtractor_9 [off]
    QUERY_RESULTS -> X2I_OfficialDocumentation_extract_Output (output)

Bookmark: XP_SpezExterneReferenz (ab 5.0)
Note: xplan:externeReferenz/xplan:XP_SpezExterneReferenz/xplan:referenzName
XMLXQueryExtractor_9 [off]
    XQUERY_TYPE = XQuery expression
    RESULT_TYPE_NAME = Single value
    WRITE_XML_HEADER = No
    RESULT_ATTRIBUTE = _result_spezExRef_referenzName
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:externeReferenz/xplan:XP_SpezExterneReferenz/xplan:referenzName)}
    XML_REMOVE_SOURCE_ATTR = No
    XML_TYPE = Attribute specifying XML
    QUERY_RESULTS -> XMLXQueryExtractor_10 [off]
Note: xplan:externeReferenz/xplan:XP_SpezExterneReferenz/xplan:georefURL
XMLXQueryExtractor_10 [off]
    XQUERY_TYPE = XQuery expression
    RESULT_TYPE_NAME = Single value
    WRITE_XML_HEADER = No
    RESULT_ATTRIBUTE = _result_spezExRef_georefURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:externeReferenz/xplan:XP_SpezExterneReferenz/xplan:georefURL)}
    XML_REMOVE_SOURCE_ATTR = No
    XML_TYPE = Attribute specifying XML
    QUERY_RESULTS -> XMLXQueryExtractor_11 [off]
Note: xplan:externeReferenz/xplan:XP_SpezExterneReferenz/xplan:referenzURL
XMLXQueryExtractor_11 [off]
    XQUERY_TYPE = XQuery expression
    RESULT_TYPE_NAME = Single value
    WRITE_XML_HEADER = No
    RESULT_ATTRIBUTE = _result_spezExRef_referenzURL
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:externeReferenz/xplan:XP_SpezExterneReferenz/xplan:referenzURL)}
    XML_REMOVE_SOURCE_ATTR = No
    XML_TYPE = Attribute specifying XML
    QUERY_RESULTS -> XMLXQueryExtractor_12 [off]
Note: xplan:externeReferenz/xplan:XP_SpezExterneReferenz/xplan:datum
XMLXQueryExtractor_12 [off]
    XQUERY_TYPE = XQuery expression
    RESULT_TYPE_NAME = Single value
    WRITE_XML_HEADER = No
    RESULT_ATTRIBUTE = _result_spezExRef_datum
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:externeReferenz/xplan:XP_SpezExterneReferenz/xplan:datum)}
    XML_REMOVE_SOURCE_ATTR = No
    XML_TYPE = Attribute specifying XML
    QUERY_RESULTS -> XMLXQueryExtractor_13 [off]
Note: xplan:externeReferenz/xplan:XP_SpezExterneReferenz/xplan:typ
XMLXQueryExtractor_13 [off]
    XQUERY_TYPE = XQuery expression
    RESULT_TYPE_NAME = Single value
    WRITE_XML_HEADER = No
    RESULT_ATTRIBUTE = _result_spezExRef_typ
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:externeReferenz/xplan:XP_SpezExterneReferenz/xplan:typ)}
    XML_REMOVE_SOURCE_ATTR = No
    XML_TYPE = Attribute specifying XML

FME custom transformer X2I_BPBereich_extract
This Transformer extracts all attributes from XPlan:BP_Bereich for transformation into the INSPIRE PLU schema 4.0.
Parameters 
_results_list_bereich{}
Output 
gml_id_BP_Bereich
result... for single attributes
results_list... for list attributes

X2I_BPBereich_extract_Input (input)
    -> PythonCaller_BP_Bereich
X2I_BPBereich_extract_Output (output)

Bookmark: XPLan:BP_Bereich
PythonCaller_BP_Bereich
    PYTHONSOURCE:
      import fme
      import fmeobjects

      def createSelectSqlScript(feature):
          listBereiche = feature.getAttribute("_results_list_bereich{}")

          sqlStrFull = "SELECT gml_id, ft_type, binary_object FROM xplan41.gml_objects WHERE gml_id LIKE '"
          sqlStrEnd = "';\n"

          for i in range(len(listBereiche)):
              ref = listBereiche[i].replace("#", "")
              sqlStrFull += ref
              sqlStrFull += sqlStrEnd

          feature.setAttribute("selectSqlScript",sqlStrFull)
    NEW_ATTRIBUTES = selectSqlScript
    PYTHONSYMBOL = createSelectSqlScript
    -> SQLExecutor [INITIATOR]
SQLExecutor
    EXPOSED_ATTRIBUTE_LIST = binary_object,gml_id
    COMBINE_ATTRS = Result Attributes Only
    COMBINE_GEOM = Initiator Geometry Only
    POSTGRES_SCHEMAS_FOR_TABLE_LISTING = xplan41
    SQL_STATEMENT = @Value(selectSqlScript)
    POSTGRES_NAMED_CONNECTION = maske_xplan4.1-test
    DATASET = maske_xplan4.1-test
    POSTGRES_QUERY_FEATURE_TYPES_FOR_MERGE_FILTERS = Yes
    FORMAT = POSTGRES
    RESULT -> TextDecoder_2
TextDecoder_2
    STRING_TO_DECODE = @Value(binary_object)
    DEST_ATTR = _decoded
    ENCODING_TYPE = HEX
    ATTR_ENCODING = utf-8
    -> XMLFormatter_2
XMLFormatter_2
    NAMESPACE_CLEANUP = No
    COLLAPSE_EMPTY_ELEMENT = No
    FORMATTING_CHOICE = Pretty-Print XML
    XML_OUTPUT_ATTR = _xml_output
    OUTPUT_ENCODING = utf-8
    REMOVE_ALL_COMMENT = No
    WHITESPACE_HANDLING = Preserve all whitespace
    SCHEMALOC_CLEANUP = No
    XML_OUTPUT_TYPE = Attribute
    XML_INPUT_TYPE = Attribute Specifying XML Text
    XML_ATTR_TEXT = _decoded
    REMOVE_EMPTY_ELEMENT = No
    TEXT_INDENT = no
    LIST_NAME = _xml_error
    INDENT_SIZE = 1
    REPLACE_TABS_WITH_SPACES = no
    PASSED -> XMLXQueryExtractor_12
Note: xplan:nachrichtlich (list) bis 4.1
XMLXQueryExtractor_12
    XQUERY_TYPE = XQuery expression
    RESULT_TYPE_NAME = List attribute
    WRITE_XML_HEADER = No
    LIST_RESULT_ATTR = _results_list_nachrichtlich
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:nachrichtlich/@xlink:href)}
    XML_REMOVE_SOURCE_ATTR = No
    XML_TYPE = Attribute specifying XML
    QUERY_RESULTS -> XMLXQueryExtractor_4
Note: xplan:rasterBasis
XMLXQueryExtractor_4
    XQUERY_TYPE = XQuery expression
    RESULT_TYPE_NAME = Single value
    WRITE_XML_HEADER = No
    RESULT_ATTRIBUTE = _result_rasterBasis
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:rasterBasis/@xlink:href)}
    XML_REMOVE_SOURCE_ATTR = No
    XML_TYPE = Attribute specifying XML
    QUERY_RESULTS -> XMLXQueryExtractor_7
    QUERY_RESULTS -> XMLXQueryExtractor_2 [off]
Note: xplan:inhaltBPlan (list) bis 4.1
XMLXQueryExtractor_7
    XQUERY_TYPE = XQuery expression
    RESULT_TYPE_NAME = List attribute
    WRITE_XML_HEADER = No
    LIST_RESULT_ATTR = _results_list_inhaltBPlan
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:inhaltBPlan/@xlink:href)}
    XML_REMOVE_SOURCE_ATTR = No
    XML_TYPE = Attribute specifying XML
    QUERY_RESULTS -> XMLXQueryExtractor_9
Note: xplan:versionBauNVO bis 4.1
XMLXQueryExtractor_9
    XQUERY_TYPE = XQuery expression
    RESULT_TYPE_NAME = Single value
    WRITE_XML_HEADER = No
    RESULT_ATTRIBUTE = _result_versionBauNVO
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:versionBauNVO)}
    XML_REMOVE_SOURCE_ATTR = No
    XML_TYPE = Attribute specifying XML
    QUERY_RESULTS -> XMLXQueryExtractor_5
Note: xplan:planinhalt (list) ab 5.0
XMLXQueryExtractor_2 [off]
    XQUERY_TYPE = XQuery expression
    RESULT_TYPE_NAME = List attribute
    WRITE_XML_HEADER = No
    LIST_RESULT_ATTR = _results_list_planinhalt
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:planinhalt/@xlink:href)}
    XML_REMOVE_SOURCE_ATTR = No
    XML_TYPE = Attribute specifying XML
    QUERY_RESULTS -> XMLXQueryExtractor_3 [off]
Note: xplan:versionBauNVODatum ab 5.0
XMLXQueryExtractor_3 [off]
    XQUERY_TYPE = XQuery expression
    RESULT_TYPE_NAME = Single value
    WRITE_XML_HEADER = No
    RESULT_ATTRIBUTE = _result_versionBauNVODatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:versionBauNVODatum)}
    XML_REMOVE_SOURCE_ATTR = No
    XML_TYPE = Attribute specifying XML
    QUERY_RESULTS -> XMLXQueryExtractor_5 [off]
Note: xplan:versionBauNVOText
XMLXQueryExtractor_5
    XQUERY_TYPE = XQuery expression
    RESULT_TYPE_NAME = Single value
    WRITE_XML_HEADER = No
    RESULT_ATTRIBUTE = _result_versionBauNVOText
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:versionBauNVOText)}
    XML_REMOVE_SOURCE_ATTR = No
    XML_TYPE = Attribute specifying XML
    QUERY_RESULTS -> XMLXQueryExtractor_10
    QUERY_RESULTS -> XMLXQueryExtractor_6 [off]
Note: xplan:versionBauGB bis 4.1
XMLXQueryExtractor_10
    XQUERY_TYPE = XQuery expression
    RESULT_TYPE_NAME = Single value
    WRITE_XML_HEADER = No
    RESULT_ATTRIBUTE = _result_versionBauGB
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:versionBauGB)}
    XML_REMOVE_SOURCE_ATTR = No
    XML_TYPE = Attribute specifying XML
    QUERY_RESULTS -> XMLXQueryExtractor_8
Note: xplan:versionBauGBDatum ab 5.0
XMLXQueryExtractor_6 [off]
    XQUERY_TYPE = XQuery expression
    RESULT_TYPE_NAME = Single value
    WRITE_XML_HEADER = No
    RESULT_ATTRIBUTE = _result_versionBauGBDatum
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:versionBauGBDatum)}
    XML_REMOVE_SOURCE_ATTR = No
    XML_TYPE = Attribute specifying XML
    QUERY_RESULTS -> XMLXQueryExtractor_8 [off]
Note: xplan:versionBauGBText
XMLXQueryExtractor_8
    XQUERY_TYPE = XQuery expression
    RESULT_TYPE_NAME = Single value
    WRITE_XML_HEADER = No
    RESULT_ATTRIBUTE = _result_versionBauGBText
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:versionBauGBText)}
    XML_REMOVE_SOURCE_ATTR = No
    XML_TYPE = Attribute specifying XML
    QUERY_RESULTS -> XMLXQueryExtractor_11
Note: xplan:gehoertZuPlan
XMLXQueryExtractor_11
    XQUERY_TYPE = XQuery expression
    RESULT_TYPE_NAME = Single value
    WRITE_XML_HEADER = No
    RESULT_ATTRIBUTE = _result_gehoertZuPlan
    XML_ATTR = _xml_output
    QUERY_EXPR:
      declare namespace xplan="http://www.xplanung.de/xplangml/4/1";
      declare namespace gml="http://www.opengis.net/gml/3.2";
      declare namespace xlink="http://www.w3.org/1999/xlink";
      for $x in /xplan:BP_Bereich
          return {data($x//xplan:gehoertZuPlan/@xlink:href)}
    XML_REMOVE_SOURCE_ATTR = No
    XML_TYPE = Attribute specifying XML
    QUERY_RESULTS -> AttributeRenamer
AttributeRenamer
    ATTR_TABLE = RENAME_SET_DEFAULT gml_id > gml_id_BP_Bereich
    -> AttributeRemover_2
AttributeRemover_2
    REMOVE_ATTRS = _decoded,binary_object,_xml_output
    -> X2I_BPBereich_extract_Output (output)

FME custom transformer X2I_ZoningElement_extract
This Transformer extracts all attributes from XPlan basic classes for transformation into the INSPIRE PLU:ZoningElement schema 4.0.
Parameters 
Xml Output: default _xml_output
Gml Id: default gml_id 
Output 
gml_id
result... for single attributes
results_list... for list attributes

Parameters:
- _XML_OUTPUT = @Value(_xml_output)   # Xml Output
- GML_ID = @Value(gml_id)   # Gml Id

X2I_ZoningElement_extract_Input (input)
    -> XMLXQueryExtractor_16
X2I_ZoningElement_extract_Output (output)

Bookmark: plu:ZoningElement
Note: xplan:position
XMLXQueryExtractor_16
    XQUERY_TYPE = XQuery expression
    RESULT_TYPE_NAME = Single value
    WRITE_XML_HEADER = No
    RESULT_ATTRIBUTE = _result_position
    XML_ATTR = _xml_output
    QUERY_EXPR:
      declare namespace xplan="http://www.xplanung.de/xplangml/4/1";
      declare namespace gml="http://www.opengis.net/gml/3.2";
      //xplan:position/*
    XML_REMOVE_SOURCE_ATTR = No
    XML_TYPE = Attribute specifying XML
    QUERY_RESULTS -> XMLXQueryExtractor_18
Note: xplan:rechtsstand
XMLXQueryExtractor_18
    XQUERY_TYPE = XQuery expression
    RESULT_TYPE_NAME = Single value
    WRITE_XML_HEADER = No
    RESULT_ATTRIBUTE = _result_rechtsstand
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:rechtsstand)}
    XML_REMOVE_SOURCE_ATTR = No
    XML_TYPE = Attribute specifying XML
    QUERY_RESULTS -> XMLXQueryExtractor_19
Note: xplan:rechtscharakter
XMLXQueryExtractor_19
    XQUERY_TYPE = XQuery expression
    RESULT_TYPE_NAME = Single value
    WRITE_XML_HEADER = No
    RESULT_ATTRIBUTE = _result_rechtscharakter
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:rechtscharakter)}
    XML_REMOVE_SOURCE_ATTR = No
    XML_TYPE = Attribute specifying XML
    QUERY_RESULTS -> XMLXQueryExtractor_25
Note: xplan:refTextInhalt (list)
XMLXQueryExtractor_25
    XQUERY_TYPE = XQuery expression
    RESULT_TYPE_NAME = List attribute
    WRITE_XML_HEADER = No
    LIST_RESULT_ATTR = _results_list_refTextInhalt
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:refTextInhalt/@xlink:href)}
    XML_REMOVE_SOURCE_ATTR = No
    XML_TYPE = Attribute specifying XML
    QUERY_RESULTS -> XMLXQueryExtractor_2
Note: xplan:hatGenerAttribut (list)
XMLXQueryExtractor_2
    XQUERY_TYPE = XQuery expression
    RESULT_TYPE_NAME = List attribute
    WRITE_XML_HEADER = No
    LIST_RESULT_ATTR = _results_list_hatGenerAttribut
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:hatGenerAttribut)}
    XML_REMOVE_SOURCE_ATTR = No
    XML_TYPE = Attribute specifying XML
    QUERY_RESULTS -> XMLXQueryExtractor_9
Note: spezielle xplan Attribute (xml)
XMLXQueryExtractor_9
    XQUERY_TYPE = XQuery expression
    RESULT_TYPE_NAME = Single value
    WRITE_XML_HEADER = No
    RESULT_ATTRIBUTE = _result_spezielleAttribute
    XML_ATTR = _xml_output
    QUERY_EXPR:
      declare namespace xplan="http://www.xplanung.de/xplangml/4/1";
      declare namespace gml="http://www.opengis.net/gml/3.2";
      <root>
       {
        for $i in /*
        return
          <out>
           {$i/xplan:MaxAnzahlWohnungen, $i/xplan:Zmin, $i/xplan:Zmax, $i/xplan:Zzwingend,$i/xplan:Z,$i/xplan:Z_Ausn,$i/xplan:Z_Staffel,$i/xplan:Z_Dach,$i/xplan:ZUmin,$i/xplan:ZUmax,$i/xplan:ZUzwingend,$i/xplan:ZU,$i/xplan:ZU_Ausn,$i/xplan:GFZmin,$i/xplan:GFZmax,$i/xplan:GFZ,$i/xplan:GFZ_Ausn,$i/xplan:BMZ,$i/xplan:BMZ_Ausn,$i/xplan:GRZ,$i/xplan:GRZmin,$i/xplan:GRZmax,$i/xplan:GRZ_Ausn,$i/xplan:Fmin,$i/xplan:Fmax,$i/xplan:Bmin,$i/xplan:Bmax,$i/xplan:Tmin,$i/xplan:Tmax,$i/xplan:GFmin,$i/xplan:GFmax,$i/xplan:GF,$i/xplan:GF_Ausn,$i/xplan:BM,$i/xplan:BM_Ausn,$i/xplan:GRmin,$i/xplan:GRmax,$i/xplan:GR,$i/xplan:GR_Ausn,$i/xplan:DNmin,$i/xplan:DNmax,$i/xplan:DN,$i/xplan:DNZwingend,$i/xplan:FR,$i/xplan:dachform,$i/xplan:ZWohn,$i/xplan:GFAntWohnen,$i/xplan:GFWohnen,$i/xplan:GFAntGewerbe,$i/xplan:GFGewerbe,$i/xplan:wohnnutzungEGStrasse,$i/xplan:bauweise,$i/xplan:bebauungsArt}
          </out>
       }
      </root>
    XML_REMOVE_SOURCE_ATTR = No
    XML_TYPE = Attribute specifying XML
    QUERY_RESULTS -> XMLXQueryExtractor_8
Note: xplan:hoehenangabe (xml)
XMLXQueryExtractor_8
    XQUERY_TYPE = XQuery expression
    RESULT_TYPE_NAME = Single value
    WRITE_XML_HEADER = No
    RESULT_ATTRIBUTE = _result_hoehenangabe
    XML_ATTR = _xml_output
    QUERY_EXPR:
      declare namespace xplan="http://www.xplanung.de/xplangml/4/1";
      declare namespace gml="http://www.opengis.net/gml/3.2";
      <root>
       {
        for $i in //xplan:hoehenangabe/xplan:XP_Hoehenangabe
        return
          <out>
           {$i/xplan:abweichenderHoehenbezug, $i/xplan:hoehenbezug, $i/xplan:abweichenderBezugspunkt, $i/xplan:bezugspunkt, $i/xplan:hMin, $i/xplan:hMax, $i/xplan:hZwingend, $i/xplan:h}
          </out>
       }
      </root>
    XML_REMOVE_SOURCE_ATTR = No
    XML_TYPE = Attribute specifying XML
    QUERY_RESULTS -> XMLXQueryExtractor_4 [off]
    QUERY_RESULTS -> XMLXQueryExtractor_5
Note: xplan:externeReferenz (list) ab 5.0
XMLXQueryExtractor_4 [off]
    XQUERY_TYPE = XQuery expression
    RESULT_TYPE_NAME = List attribute
    WRITE_XML_HEADER = No
    LIST_RESULT_ATTR = _results_list_externeReferenz
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:externeReferenz/@xlink:href)}
    XML_REMOVE_SOURCE_ATTR = No
    XML_TYPE = Attribute specifying XML
    QUERY_RESULTS -> XMLXQueryExtractor_5 [off]
Note: xplan:refBegruendungInhalt (list)
XMLXQueryExtractor_5
    XQUERY_TYPE = XQuery expression
    RESULT_TYPE_NAME = List attribute
    WRITE_XML_HEADER = No
    LIST_RESULT_ATTR = _results_list_refBegruendungInhalt
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:refBegruendungInhalt)}
    XML_REMOVE_SOURCE_ATTR = No
    XML_TYPE = Attribute specifying XML
    QUERY_RESULTS -> XMLXQueryExtractor_6
Note: xplan:startBedingung
XMLXQueryExtractor_6
    XQUERY_TYPE = XQuery expression
    RESULT_TYPE_NAME = Single value
    WRITE_XML_HEADER = No
    RESULT_ATTRIBUTE = _result_startBedingung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:startBedingung)}
    XML_REMOVE_SOURCE_ATTR = No
    XML_TYPE = Attribute specifying XML
    QUERY_RESULTS -> XMLXQueryExtractor_7
Note: xplan:endeBedingung
XMLXQueryExtractor_7
    XQUERY_TYPE = XQuery expression
    RESULT_TYPE_NAME = Single value
    WRITE_XML_HEADER = No
    RESULT_ATTRIBUTE = _result_endeBedingung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:endeBedingung)}
    XML_REMOVE_SOURCE_ATTR = No
    XML_TYPE = Attribute specifying XML
    QUERY_RESULTS -> XMLXQueryExtractor_21
AttributeRemover
    REMOVE_ATTRS = _xml_output
    -> X2I_ZoningElement_extract_Output (output)

Bookmark: hilucs landuse
Note: xplan:allgArtDerBaulNutzung
XMLXQueryExtractor_21
    XQUERY_TYPE = XQuery expression
    RESULT_TYPE_NAME = Single value
    WRITE_XML_HEADER = No
    RESULT_ATTRIBUTE = _result_allgArtDerBaulNutzung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:allgArtDerBaulNutzung)}
    XML_REMOVE_SOURCE_ATTR = No
    XML_TYPE = Attribute specifying XML
    QUERY_RESULTS -> XMLXQueryExtractor_22
Note: xplan:besondereArtDerBaulNutzung
XMLXQueryExtractor_22
    XQUERY_TYPE = XQuery expression
    RESULT_TYPE_NAME = Single value
    WRITE_XML_HEADER = No
    RESULT_ATTRIBUTE = _result_besondereArtDerBaulNutzung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:besondereArtDerBaulNutzung)}
    XML_REMOVE_SOURCE_ATTR = No
    XML_TYPE = Attribute specifying XML
    QUERY_RESULTS -> XMLXQueryExtractor_23
Note: xplan:nutzungsform
XMLXQueryExtractor_23
    XQUERY_TYPE = XQuery expression
    RESULT_TYPE_NAME = Single value
    WRITE_XML_HEADER = No
    RESULT_ATTRIBUTE = _result_nutzungsform
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:nutzungsform)}
    XML_REMOVE_SOURCE_ATTR = No
    XML_TYPE = Attribute specifying XML
    QUERY_RESULTS -> XMLXQueryExtractor_24
Note: xplan:ziel
XMLXQueryExtractor_24
    XQUERY_TYPE = XQuery expression
    RESULT_TYPE_NAME = Single value
    WRITE_XML_HEADER = No
    RESULT_ATTRIBUTE = _result_ziel
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:ziel)}
    XML_REMOVE_SOURCE_ATTR = No
    XML_TYPE = Attribute specifying XML
    QUERY_RESULTS -> XMLXQueryExtractor_20
Note: xplan:zweckbestimmung
XMLXQueryExtractor_20
    XQUERY_TYPE = XQuery expression
    RESULT_TYPE_NAME = Single value
    WRITE_XML_HEADER = No
    RESULT_ATTRIBUTE = _result_zweckbestimmung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:zweckbestimmung)}
    XML_REMOVE_SOURCE_ATTR = No
    XML_TYPE = Attribute specifying XML
    QUERY_RESULTS -> AttributeRemover

FME custom transformer X2I_SupplementaryRegulation_extract
This Transformer extracts all attributes from XPlan basic classes for transformation into the INSPIRE PLU:SupplementaryRegulation schema 4.0.
Parameters 
Xml Output: default _xml_output
Gml Id: default gml_id 
Output 
gml_id
result... for single attributes
results_list... for list attributes

Parameters:
- _XML_OUTPUT = @Value(_xml_output)   # Xml Output
- GML_ID = @Value(gml_id)   # Gml Id

X2I_SupplementaryRegulation_extract_Input (input)
    -> XMLXQueryExtractor_16
X2I_SupplementaryRegulation_extract_Output (output)

Bookmark: plu:SupplementaryRegulation
Note: xplan:position
XMLXQueryExtractor_16
    XQUERY_TYPE = XQuery expression
    RESULT_TYPE_NAME = Single value
    WRITE_XML_HEADER = No
    RESULT_ATTRIBUTE = _result_position
    XML_ATTR = _xml_output
    QUERY_EXPR:
      declare namespace xplan="http://www.xplanung.de/xplangml/4/1";
      declare namespace gml="http://www.opengis.net/gml/3.2";
      //xplan:position/*
    XML_REMOVE_SOURCE_ATTR = No
    XML_TYPE = Attribute specifying XML
    QUERY_RESULTS -> XMLXQueryExtractor_18
Note: xplan:rechtsstand
XMLXQueryExtractor_18
    XQUERY_TYPE = XQuery expression
    RESULT_TYPE_NAME = Single value
    WRITE_XML_HEADER = No
    RESULT_ATTRIBUTE = _result_rechtsstand
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:rechtsstand)}
    XML_REMOVE_SOURCE_ATTR = No
    XML_TYPE = Attribute specifying XML
    QUERY_RESULTS -> XMLXQueryExtractor_19
Note: xplan:rechtscharakter
XMLXQueryExtractor_19
    XQUERY_TYPE = XQuery expression
    RESULT_TYPE_NAME = Single value
    WRITE_XML_HEADER = No
    RESULT_ATTRIBUTE = _result_rechtscharakter
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:rechtscharakter)}
    XML_REMOVE_SOURCE_ATTR = No
    XML_TYPE = Attribute specifying XML
    QUERY_RESULTS -> XMLXQueryExtractor_25
Note: xplan:refTextInhalt (list)
XMLXQueryExtractor_25
    XQUERY_TYPE = XQuery expression
    RESULT_TYPE_NAME = List attribute
    WRITE_XML_HEADER = No
    LIST_RESULT_ATTR = _results_list_refTextInhalt
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:refTextInhalt/@xlink:href)}
    XML_REMOVE_SOURCE_ATTR = No
    XML_TYPE = Attribute specifying XML
    QUERY_RESULTS -> XMLXQueryExtractor_2
Note: xplan:hatGenerAttribut (list)
XMLXQueryExtractor_2
    XQUERY_TYPE = XQuery expression
    RESULT_TYPE_NAME = List attribute
    WRITE_XML_HEADER = No
    LIST_RESULT_ATTR = _results_list_hatGenerAttribut
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:hatGenerAttribut)}
    XML_REMOVE_SOURCE_ATTR = No
    XML_TYPE = Attribute specifying XML
    QUERY_RESULTS -> XMLXQueryExtractor_9
Note: spezielle xplan Attribute (xml)
XMLXQueryExtractor_9
    XQUERY_TYPE = XQuery expression
    RESULT_TYPE_NAME = Single value
    WRITE_XML_HEADER = No
    RESULT_ATTRIBUTE = _result_spezielleAttribute
    XML_ATTR = _xml_output
    QUERY_EXPR:
      declare namespace xplan="http://www.xplanung.de/xplangml/4/1";
      declare namespace gml="http://www.opengis.net/gml/3.2";
      <root>
       {
        for $i in /*
        return
          <out>
           {$i/xplan:MaxAnzahlWohnungen, $i/xplan:Zmin, $i/xplan:Zmax, $i/xplan:Zzwingend,$i/xplan:Z,$i/xplan:Z_Ausn,$i/xplan:Z_Staffel,$i/xplan:Z_Dach,$i/xplan:ZUmin,$i/xplan:ZUmax,$i/xplan:ZUzwingend,$i/xplan:ZU,$i/xplan:ZU_Ausn,$i/xplan:GFZmin,$i/xplan:GFZmax,$i/xplan:GFZ,$i/xplan:GFZ_Ausn,$i/xplan:BMZ,$i/xplan:BMZ_Ausn,$i/xplan:GRZ,$i/xplan:GRZmin,$i/xplan:GRZmax,$i/xplan:GRZ_Ausn,$i/xplan:Fmin,$i/xplan:Fmax,$i/xplan:Bmin,$i/xplan:Bmax,$i/xplan:Tmin,$i/xplan:Tmax,$i/xplan:GFmin,$i/xplan:GFmax,$i/xplan:GF,$i/xplan:GF_Ausn,$i/xplan:BM,$i/xplan:BM_Ausn,$i/xplan:GRmin,$i/xplan:GRmax,$i/xplan:GR,$i/xplan:GR_Ausn,$i/xplan:DNmin,$i/xplan:DNmax,$i/xplan:DN,$i/xplan:DNZwingend,$i/xplan:FR,$i/xplan:dachform,$i/xplan:ZWohn,$i/xplan:GFAntWohnen,$i/xplan:GFWohnen,$i/xplan:GFAntGewerbe,$i/xplan:GFGewerbe,$i/xplan:wohnnutzungEGStrasse,$i/xplan:bauweise,$i/xplan:bebauungsArt}
          </out>
       }
      </root>
    XML_REMOVE_SOURCE_ATTR = No
    XML_TYPE = Attribute specifying XML
    QUERY_RESULTS -> XMLXQueryExtractor_8
Note: xplan:hoehenangabe (xml)
XMLXQueryExtractor_8
    XQUERY_TYPE = XQuery expression
    RESULT_TYPE_NAME = Single value
    WRITE_XML_HEADER = No
    RESULT_ATTRIBUTE = _result_hoehenangabe
    XML_ATTR = _xml_output
    QUERY_EXPR:
      declare namespace xplan="http://www.xplanung.de/xplangml/4/1";
      declare namespace gml="http://www.opengis.net/gml/3.2";
      <root>
       {
        for $i in //xplan:hoehenangabe/xplan:XP_Hoehenangabe
        return
          <out>
           {$i/xplan:abweichenderHoehenbezug, $i/xplan:hoehenbezug, $i/xplan:abweichenderBezugspunkt, $i/xplan:bezugspunkt, $i/xplan:hMin, $i/xplan:hMax, $i/xplan:hZwingend, $i/xplan:h}
          </out>
       }
      </root>
    XML_REMOVE_SOURCE_ATTR = No
    XML_TYPE = Attribute specifying XML
    QUERY_RESULTS -> XMLXQueryExtractor_5
    QUERY_RESULTS -> XMLXQueryExtractor_4 [off]
Note: xplan:externeReferenz (list) ab 5.0
XMLXQueryExtractor_4 [off]
    XQUERY_TYPE = XQuery expression
    RESULT_TYPE_NAME = List attribute
    WRITE_XML_HEADER = No
    LIST_RESULT_ATTR = _results_list_externeReferenz
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:externeReferenz/@xlink:href)}
    XML_REMOVE_SOURCE_ATTR = No
    XML_TYPE = Attribute specifying XML
    QUERY_RESULTS -> XMLXQueryExtractor_5 [off]
Note: xplan:refBegruendungInhalt (list)
XMLXQueryExtractor_5
    XQUERY_TYPE = XQuery expression
    RESULT_TYPE_NAME = List attribute
    WRITE_XML_HEADER = No
    LIST_RESULT_ATTR = _results_list_refBegruendungInhalt
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x//xplan:refBegruendungInhalt)}
    XML_REMOVE_SOURCE_ATTR = No
    XML_TYPE = Attribute specifying XML
    QUERY_RESULTS -> XMLXQueryExtractor_6
Note: xplan:startBedingung
XMLXQueryExtractor_6
    XQUERY_TYPE = XQuery expression
    RESULT_TYPE_NAME = Single value
    WRITE_XML_HEADER = No
    RESULT_ATTRIBUTE = _result_startBedingung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:startBedingung)}
    XML_REMOVE_SOURCE_ATTR = No
    XML_TYPE = Attribute specifying XML
    QUERY_RESULTS -> XMLXQueryExtractor_7
Note: xplan:endeBedingung
XMLXQueryExtractor_7
    XQUERY_TYPE = XQuery expression
    RESULT_TYPE_NAME = Single value
    WRITE_XML_HEADER = No
    RESULT_ATTRIBUTE = _result_endeBedingung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:endeBedingung)}
    XML_REMOVE_SOURCE_ATTR = No
    XML_TYPE = Attribute specifying XML
    QUERY_RESULTS -> XMLXQueryExtractor_21
AttributeRemover_4
    REMOVE_ATTRS = _xml_output
    -> X2I_SupplementaryRegulation_extract_Output (output)

Bookmark: hilucs landuse
Note: xplan:allgArtDerBaulNutzung
XMLXQueryExtractor_21
    XQUERY_TYPE = XQuery expression
    RESULT_TYPE_NAME = Single value
    WRITE_XML_HEADER = No
    RESULT_ATTRIBUTE = _result_allgArtDerBaulNutzung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:allgArtDerBaulNutzung)}
    XML_REMOVE_SOURCE_ATTR = No
    XML_TYPE = Attribute specifying XML
    QUERY_RESULTS -> XMLXQueryExtractor_22
Note: xplan:besondereArtDerBaulNutzung
XMLXQueryExtractor_22
    XQUERY_TYPE = XQuery expression
    RESULT_TYPE_NAME = Single value
    WRITE_XML_HEADER = No
    RESULT_ATTRIBUTE = _result_besondereArtDerBaulNutzung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:besondereArtDerBaulNutzung)}
    XML_REMOVE_SOURCE_ATTR = No
    XML_TYPE = Attribute specifying XML
    QUERY_RESULTS -> XMLXQueryExtractor_23
Note: xplan:nutzungsform
XMLXQueryExtractor_23
    XQUERY_TYPE = XQuery expression
    RESULT_TYPE_NAME = Single value
    WRITE_XML_HEADER = No
    RESULT_ATTRIBUTE = _result_nutzungsform
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:nutzungsform)}
    XML_REMOVE_SOURCE_ATTR = No
    XML_TYPE = Attribute specifying XML
    QUERY_RESULTS -> XMLXQueryExtractor_24
Note: xplan:ziel
XMLXQueryExtractor_24
    XQUERY_TYPE = XQuery expression
    RESULT_TYPE_NAME = Single value
    WRITE_XML_HEADER = No
    RESULT_ATTRIBUTE = _result_ziel
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:ziel)}
    XML_REMOVE_SOURCE_ATTR = No
    XML_TYPE = Attribute specifying XML
    QUERY_RESULTS -> XMLXQueryExtractor_20
Note: xplan:zweckbestimmung
XMLXQueryExtractor_20
    XQUERY_TYPE = XQuery expression
    RESULT_TYPE_NAME = Single value
    WRITE_XML_HEADER = No
    RESULT_ATTRIBUTE = _result_zweckbestimmung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:zweckbestimmung)}
    XML_REMOVE_SOURCE_ATTR = No
    XML_TYPE = Attribute specifying XML
    QUERY_RESULTS -> XMLXQueryExtractor_34
Note: xplan:grund
XMLXQueryExtractor_34
    XQUERY_TYPE = XQuery expression
    RESULT_TYPE_NAME = Single value
    WRITE_XML_HEADER = No
    RESULT_ATTRIBUTE = _result_grund
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:grund)}
    XML_REMOVE_SOURCE_ATTR = No
    XML_TYPE = Attribute specifying XML
    QUERY_RESULTS -> XMLXQueryExtractor_35
Note: xplan:massnahme
XMLXQueryExtractor_35
    XQUERY_TYPE = XQuery expression
    RESULT_TYPE_NAME = Single value
    WRITE_XML_HEADER = No
    RESULT_ATTRIBUTE = _result_massnahme
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:massnahme)}
    XML_REMOVE_SOURCE_ATTR = No
    XML_TYPE = Attribute specifying XML
    QUERY_RESULTS -> XMLXQueryExtractor_36
Note: xplan:typ
XMLXQueryExtractor_36
    XQUERY_TYPE = XQuery expression
    RESULT_TYPE_NAME = Single value
    WRITE_XML_HEADER = No
    RESULT_ATTRIBUTE = _result_typ
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:typ)}
    XML_REMOVE_SOURCE_ATTR = No
    XML_TYPE = Attribute specifying XML
    QUERY_RESULTS -> XMLXQueryExtractor_37
Note: xplan:verlaengerung
XMLXQueryExtractor_37
    XQUERY_TYPE = XQuery expression
    RESULT_TYPE_NAME = Single value
    WRITE_XML_HEADER = No
    RESULT_ATTRIBUTE = _result_verlaengerung
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:verlaengerung)}
    XML_REMOVE_SOURCE_ATTR = No
    XML_TYPE = Attribute specifying XML
    QUERY_RESULTS -> XMLXQueryExtractor_38
Note: xplan:zulaessigkeit
XMLXQueryExtractor_38
    XQUERY_TYPE = XQuery expression
    RESULT_TYPE_NAME = Single value
    WRITE_XML_HEADER = No
    RESULT_ATTRIBUTE = _result_zulaessigkeit
    XML_ATTR = _xml_output
    QUERY_EXPR:
      declare namespace xplan="http://www.xplanung.de/xplangml/4/1";
      declare namespace gml="http://www.opengis.net/gml/3.2";
      declare namespace xlink="http://www.w3.org/1999/xlink";
      for $x in /*
          return {data($x/xplan:zulaessigkeit)}
    XML_REMOVE_SOURCE_ATTR = No
    XML_TYPE = Attribute specifying XML
    QUERY_RESULTS -> AttributeRemover_4
